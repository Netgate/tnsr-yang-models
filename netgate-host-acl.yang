module netgate-host-acl {

    yang-version 1.1;

    namespace "urn:netgate:xml:yang:netgate-host-acl";
    prefix "nghost";

    import clixon-lib {
	prefix "cl";
    }

    import ietf-inet-types {
	prefix "inet";
    }

    import ietf-yang-types {
	prefix "yang";
    }

    import netgate-cli-extensions {
	prefix "ngcliext";
    }

    import netgate-common {
	prefix "ngcom";
    }

    organization "Netgate";

    contact "Web: <http://www.netgate.com>";

    description
	"This YANG module provides a data model for host ACL data.

	 Copyright 2019-2022, 2025 Rubicon Communications, LLC.
	";

    revision 2025-02-01 {
	description
	    "TNSR Release 25.02.";
    }

    revision 2022-02-15 {
	description
	    "TNSR Release 22.02.";
    }

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-08-30 {
	description
	    "TNSR Release 19.08.";
    }

    revision 2019-05-30 {
	description
	    "TNSR Release 19.05.";
    }

    revision 2019-02-15 {
	description
	    "TNSR Release 19.02.";
    }

    revision 2019-02-07 {
	description
	    "Initial revision.";
    }

    typedef host-acl-protocol-name {
	type enumeration {
	    enum icmp {
		description
		    "Internet Control Message Protocol (ICMP).";
	    }

	    enum tcp {
		description
		    "Transmission Control Protocol (TCP).";
	    }

	    enum udp {
		description
		    "User Datagram Protocol (UDP).";
	    }
	}
    }

    typedef host-acl-protocol-number {
	type uint8;
	description
	    "Host acl protocol number.";
    }

    typedef host-acl-protocol {
	type union {
	    type host-acl-protocol-name;
	    type host-acl-protocol-number;
	}
    }


    typedef host-acl-icmp-type {
	type enumeration {
	    enum echo-reply {
		description
		    "Echo reply.";
	    }

	    enum destination-unreachable {
		description
		    "Destination unreachable.";
	    }

	    enum source-quench {
		description
		    "Source quench.";
	    }

	    enum redirect {
		description
		    "Redirect.";
	    }

	    enum echo-request {
		description
		    "Echo request.";
	    }

	    enum time-exceeded {
		description
		    "Time exceeded.";
	    }

	    enum parameter-problem {
		description
		    "Parameter problem.";
	    }

	    enum timestamp-request {
		description
		    "Timestamp request.";
	    }

	    enum timestamp-reply {
		description
		    "Timestamp reply.";
	    }

	    enum info-request {
		description
		    "Info request.";
	    }

	    enum info-reply {
		description
		    "Info reply.";
	    }

	    enum address-mask-request {
		description
		    "Address mask request.";
	    }

	    enum address-mask-reply {
		description
		    "Address mask reply.";
	    }

	    enum router-advertisement {
		description
		    "Router advertisement.";
	    }

	    enum router-solicitation {
		description
		    "Router solicitation.";
	    }
	}
    }

    typedef host-acl-icmpv6-type {
	type enumeration {
	    enum destination-unreachable {
		description
		    "Destination unreachable.";
	    }

	    enum packet-too-big {
		description
		    "Packet too big.";
	    }

	    enum time-exceeded {
		description
		    "Time exceeded.";
	    }

	    enum echo-request {
		description
		    "Echo request.";
	    }

	    enum echo-reply {
		description
		    "Echo reply.";
	    }

	    enum mld-listener-query {
		description
		    "MLD listener query.";
	    }

	    enum mld-listener-report {
		description
		    "MLD listener report.";
	    }

	    enum mld-listener-reduction {
		description
		    "MLD listener reduction.";
	    }

	    enum nd-router-solicit {
		description
		    "ND router solicit.";
	    }

	    enum nd-router-advert {
		description
		    "ND router advert.";
	    }

	    enum nd-neighbor-solicit {
		description
		    "ND neighbor solicit.";
	    }

	    enum nd-neighbor-advert {
		description
		    "ND neighbor advert.";
	    }

	    enum nd-redirect {
		description
		    "ND redirect.";
	    }

	    enum parameter-problem {
		description
		    "Parameter problem.";
	    }

	    enum router-renumbering {
		description
		    "Router renumbering.";
	    }
	}
    }

    typedef host-acl-action {
	type enumeration {
	    enum permit {
		description
		    "Permit.";
	    }

	    enum deny {
		description
		    "Deny.";
	    }
	}
    }

    container host-config {
	description
	    "Host configuration parameters.";

	container security {
	    description
		"Host security configuration parameters.";

	    container host-acls {
		description
		    "Host access lists (ACLs).";

		list host-acl {
		    key "acl-name";

		    description
			"The list of configured host ACLs.";

		    ngcliext:node-fmt "host acl @{acl-name}$n";
		    ngcliext:pre-children-op "push";

		    leaf acl-name {
			type ngcom:identifier-63;
			description
			    "The name of the host ACL.";
		    }

		    leaf acl-seq {
			type uint32;
			description
			    "The sequence number of the host ACL.";
			ngcliext:node-fmt "^sequence @@$n";
		    }

		    leaf description {
			type ngcom:description-63;
			description
			    "The description of the host ACL.";
			ngcliext:node-fmt "^$% @@$n";
			cl:ignore-compare;
		    }

		    list acl-rule {
			key "rule-seq";

			description
			    "The list of the host ACL rules.";

			ngcliext:node-fmt "^rule @{rule-seq}$n";
			ngcliext:pre-children-op "push";

			leaf rule-seq {
			    type uint32;
			    description
				"The sequence number of the rule.";
			}

			leaf description {
			    type ngcom:description-63;
			    description
				"The description of the rule.";
			    ngcliext:node-fmt "^$% @@$n";
			    cl:ignore-compare;
			}

			container packet-match {
			    description
				"The matching packets of the rule.";

			    ngcliext:parent-fmt "^match";

			    leaf input-if {
				type ngcom:identifier-31;
				description
				    "The input interface name.";
				ngcliext:node-fmt "$< input-interface @@$n";
			    }

			    container link {
				description
				    "Ethernet traffic match.";

				ngcliext:parent-fmt "$< mac address";

				leaf source {
				    type yang:mac-address;
				    description
					"The source MAC address.";
				    ngcliext:node-fmt "$< $% @@$n";
				}

				leaf destination {
				    type yang:mac-address;
				    description
					"The destination MAC address.";
				    ngcliext:node-fmt "$< $% @@$n";
				}
			    }

			    container ip {
				description
				    "IP traffic match.";

				ngcliext:parent-fmt "$< ip";

				leaf version {
				    type uint8 {
					range "4 | 6";
				    }
				    description
					"IP version.";
				    ngcliext:node-fmt "$< $% @@$n";
				}

				leaf protocol {
				    type host-acl-protocol;
				    description
					"The IP protocol.";
				    ngcliext:node-fmt "$< $% @@$n";
				}

				leaf source {
				    type inet:ip-prefix;
				    description
					"The source IP prefix.";
				    ngcliext:node-fmt "$< address $% @@$n";
				}

				leaf destination {
				    type inet:ip-prefix;
				    description
					"The destination IP prefix.";
				    ngcliext:node-fmt "$< address $% @@$n";
				}

				container transport {
				    description
					"Transport options.";

				    ngcliext:parent-fmt "$<";

				    container source-port {
					description
					    "The source port range.";

					ngcliext:parent-fmt "$< port source";

					leaf first {
					    type inet:port-number;
					    description
						"The first port number.";
					    ngcliext:node-op "test-set:%{last}";
					    ngcliext:node-fmt "$< @@$n|$< range start @@ end %{last}$n";
					}

					leaf last {
					    type inet:port-number;
					    description
						"The last port number.";
					    ngcliext:sibling-fmt "@@";
					}
				    }

				    container destination-port {
					description
					    "The destination port range.";

					ngcliext:parent-fmt "$< port destination";

					leaf first {
					    type inet:port-number;
					    description
						"The first port number.";
					    ngcliext:sibling-fmt "@@";
					    ngcliext:node-op "bool";
					    ngcliext:node-fmt "|$< @@$n";
					}

					leaf last {
					    type inet:port-number;
					    description
						"The last port number.";
					    ngcliext:node-op "bool";
					    ngcliext:node-fmt "|$< range start %{first} end @@$n";
					}
				    }

				    container tcp {
					description
					    "TCP options.";

					ngcliext:parent-fmt "$< tcp";

					container flags {
					    description
						"TCP flags.";

					    ngcliext:parent-fmt "$< flag";

					    leaf cwr {
						type boolean;
						description
						    "Congestion
						     Window Reduced.";
						ngcliext:node-fmt "$< $%$n";
					    }

					    leaf ece {
						type boolean;
						description
						    "ECN-Echo.";
						ngcliext:node-fmt "$< $%$n";
					    }

					    leaf urg {
						type boolean;
						description
						    "Urgent.";
						ngcliext:node-fmt "$< $%$n";
					    }

					    leaf ack {
						type boolean;
						description
						    "Acknowledgment.";
						ngcliext:node-fmt "$< $%$n";
					    }

					    leaf psh {
						type boolean;
						description
						    "Push.";
						ngcliext:node-fmt "$< $%$n";
					    }

					    leaf rst {
						type boolean;
						description
						    "Reset.";
						ngcliext:node-fmt "$< $%$n";
					    }

					    leaf syn {
						type boolean;
						description
						    "Synchronize.";
						ngcliext:node-fmt "$< $%$n";
					    }

					    leaf fin {
						type boolean;
						description
						    "Finished.";
						ngcliext:node-fmt "$< $%$n";
					    }
					}
				    }

				    container icmp {
					description
					    "ICMP options.";

					ngcliext:parent-fmt "$< icmp";

					choice type {
					    case ipv4 {
						leaf icmp-type {
						    type host-acl-icmp-type;
						    description
							"ICMP type.";
						    ngcliext:node-fmt "$< type @@%{code}$n";
						}
					    }

					    case ipv6 {
						leaf icmpv6-type {
						    type host-acl-icmpv6-type;
						    description
							"ICMPv6 type.";
						    ngcliext:node-fmt "$< type @@%{code}$n";
						}
					    }
					}

					leaf code {
					    type uint8;
					    description
						"ICMP code.";
					    ngcliext:sibling-fmt " code @@";
					}
				    }
				}
			    }
			}

			leaf action {
			    type host-acl-action;
			    mandatory true;
			    description
				"The action of the rule.";
			    ngcliext:node-fmt "^$% @@$n";
			}
		    }
		}
	    }
	}
    }

    container host-state {
	config false;
	description
	    "Host state parameters.";

	container security {
	    description
		"Host security state parameters.";

	    container host-acls {
		description
		    "Host access lists (ACLs).";

		list host-acl {
		    key "acl-name";

		    description
			"The list of configured host ACLs.";

		    leaf acl-name {
			    type ngcom:identifier-63;
			    description
				"The name of the host ACL.";
		    }

		    leaf acl-seq {
			    type uint32;
			    description
				"The sequence number of the host ACL.";
		    }

		    leaf description {
			    type ngcom:description-63;
			    description
				"The description of the host ACL.";
		    }

		    list acl-rule {
			key "rule-seq";

			description
			    "The list of the host ACL rules.";

			leaf rule-seq {
			    type uint32;
			    description
				"The sequence number of the rule.";
			}

			leaf description {
			    type ngcom:description-63;
			    description
				"The description of the rule.";
			}

			container packet-match {
			    description
				"The matching packets of the rule.";

			    leaf input-if {
				type ngcom:identifier-31;
				description
				    "The input interface name.";
			    }

			    container link {
				description
				    "Ethernet traffic match.";

				leaf source {
				    type yang:mac-address;
				    description
					"The source MAC address.";
				}

				leaf destination {
				    type yang:mac-address;
				    description
					"The destination MAC address.";
				}
			    }

			    container ip {
				description
				    "IP traffic match.";

				leaf version {
				    type uint8 {
					range "4 | 6";
				    }
				    description
					"IP version.";
				}

				leaf protocol {
				    type host-acl-protocol;
				    description
					"The IP protocol.";
				}

				leaf source {
				    type inet:ip-prefix;
				    description
					"The source IP prefix.";
				}

				leaf destination {
				    type inet:ip-prefix;
				    description
					"The destination IP prefix.";
				}

				container transport {
				    description
					"Transport options.";

				    container source-port {
					description
					    "The source port range.";

					leaf first {
					    type inet:port-number;
					    description
						"The first port number.";
					}

					leaf last {
					    type inet:port-number;
					    description
						"The last port number.";
					}
				    }

				    container destination-port {
					description
					    "The destination port range.";

					leaf first {
					    type inet:port-number;
					    description
						"The first port number.";
					}

					leaf last {
					    type inet:port-number;
					    description
						"The last port number.";
					}
				    }

				    container tcp {
					description
					    "TCP options.";

					container flags {
					    description
						"TCP flags.";

					    leaf cwr {
						type boolean;
						description
						    "Congestion
						     Window Reduced.";
					    }

					    leaf ece {
						type boolean;
						description
						    "ECN-Echo.";
					    }

					    leaf urg {
						type boolean;
						description
						    "Urgent.";
					    }

					    leaf ack {
						type boolean;
						description
						    "Acknowledgment.";
					    }

					    leaf psh {
						type boolean;
						description
						    "Push.";
					    }

					    leaf rst {
						type boolean;
						description
						    "Reset.";
					    }

					    leaf syn {
						type boolean;
						description
						    "Synchronize.";
					    }

					    leaf fin {
						type boolean;
						description
						    "Finished.";
					    }
					}
				    }

				    container icmp {
					description
					    "ICMP options.";

					choice type {
					    case ipv4 {
						leaf icmp-type {
						    type host-acl-icmp-type;
						    description
							"ICMP type.";
						}
					    }

					    case ipv6 {
						leaf icmpv6-type {
						    type host-acl-icmpv6-type;
						    description
							"ICMPv6 type.";
						}
					    }
					}

					leaf code {
					    type uint8;
					    description
						"ICMP code.";
					}
				    }
				}
			    }
			}

			leaf action {
			    type host-acl-action;
			    mandatory true;
			    description
				"The action of the rule.";
			}

			leaf total-bytes {
			    type uint64;
			    description
				"Count of bytes matched.";
			}

			leaf total-packets {
			    type uint32;
			    description
				"Count of packets matched.";
			}
		    }
		}
	    }
	}
    }
}
