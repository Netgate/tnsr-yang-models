module netgate-route-table {

    yang-version 1.1;

    namespace "urn:netgate:xml:yang:netgate-route-table";
    prefix "ngrttab";

    import clixon-lib {
	prefix "cl";
    }

    import ietf-inet-types {
	prefix "inet";
    }

    import netgate-cli-extensions {
	prefix "ngcliext";
    }

    import netgate-common {
	prefix "ngcom";
    }

    organization "Netgate";

    contact "Web: <http://www.netgate.com>";

    description
	"This YANG module provides a Netgate-defined data-model
	 for Route Tables.

	 Copyright 2017-2025 Rubicon Communications, LLC.";

    revision 2025-02-01 {
	description
	    "TNSR Release 25.02.";
    }

    revision 2024-10-01 {
	description
	    "TNSR Release 24.10.";
    }

    revision 2024-06-01 {
	description
	    "TNSR Release 24.06.";
    }

    revision 2023-02-15 {
	description
	    "TNSR Release 23.02.";
    }

    revision 2022-02-15 {
	description
	    "TNSR Release 22.02.";
    }

    revision 2021-06-15 {
	description
	    "TNSR Release 21.07.";
    }

    revision 2021-02-15 {
	description
	    "TNSR Release 21.02.";
    }

    revision 2020-07-15 {
	description
	    "TNSR Release 20.07.";
    }

    revision 2020-06-15 {
	description
	    "TNSR Release 20.06.";
    }

    revision 2020-02-15 {
	description
	    "TNSR Release 20.02.";
    }

    revision 2019-02-15 {
	description
	    "TNSR Release 19.02.";
    }

    revision 2017-08-26 {
	description
	    "Initial Revision.";
    }

    typedef route-table-id {
	type union {
	    type enumeration {
		enum "default";
	    }
	    type leafref {
		path "/ngrttab:route-table-config" +
		     "/ngrttab:static-routes" +
		     "/ngrttab:route-table" +
		     "/ngrttab:name";
	    }
	}
    }

    typedef route-class {
	type enumeration {
	    enum special-default {
		description
		    "Special routes automatically added in any route table
		     by default.";
	    }
	    enum special-neighbor {
		description
		    "Special routes automatically added for any discovered
		     neighbor.";
	    }
	    enum special-connected {
		description
		    "Special routes automatically added after an IP address
		     is assigned to an interface.";
	    }
	    enum special-drop {
		description
		    "Special drop routes automatically added after an IP address
		     is assigned to an interface.";
	    }
	    enum connected {
		description
		    "Connected routes.";
	    }
	    enum static {
		description
		    "Static routes.";
	    }
	    enum dynamic {
		description
		    "Dynamic routes.";
	    }
	}
    }

    rpc route-lookup {
	input {
	    leaf table-name {
		type ngcom:rt-identifier-63;
		description
		    "The name of a Route Table.";
		mandatory true;
	    }

	    leaf prefix {
		type inet:ip-prefix;
		description
		    "A prefix to lookup.";
		mandatory true;
	    }

	    leaf exact {
		type boolean;
		description
		    "If present and true, the lookup must match exactly.";
	    }
	}

	output {
	    container route {
		description
		    "Route matching prefix lookup.";

		leaf table-name {
		    type string;
		    description
			"Name of the route table containing the route.";
		}

		leaf table-id {
		    type uint32;
		    description
			"Id of the route table containing the route.";
		}

		leaf destination-prefix {
		    type inet:ip-prefix;
		    description
			"IP destination prefix";
		}

		leaf priority {
		    type uint8;
		    description
			"Administrative distance preference.";
		}

		container paths {

		    list path {
			key path-id;

			leaf path-id {
			    type uint32;
			}

			leaf if-name {
			    type string;
			    description
				"Name of the interface.";
			}

			leaf ip-address {
			    type inet:ip-address-no-zone;
			    description
				"The next hop IP address.";
			}

			leaf weight {
			    type uint8;
			    description
				"Multipath route weight.";
			}

			leaf drop {
			    type boolean;
			    description
				"Drop the packet.";
			}

			leaf local {
			    type boolean;
			    description
				"Receive the packet locally.";
			}

			leaf null-send-unreach {
			    type boolean;
			    description
				"Drop packet with an 'unreachable' reply.";
			}

			leaf null-send-prohibit {
			    type boolean;
			    description
				"Drop packet with a 'prohibited' reply.";
			}
		    }
		}
	    }
	}
    }


    container route-table-config {
	description
	    "Route Table define a set of static IPv4 and IPv6 routes.";

	container static-routes {
	    description
		"Static routes.";

	    list route-table {
		key "name";
		description
		    "Route table entries are indexed by their name.
		     Table names are unique across all address families.";

		ngcliext:node-fmt "route table @{name}$n";
		ngcliext:pre-children-op "push";
		ngcliext:post-node-fmt "$n";

		leaf name {
		    type ngcom:rt-identifier-15;
		    description
			"The name of a Route Table.";
		}

		leaf description {
		    type ngcom:description-63;
		    description
			"A description of the route table.";
		    ngcliext:context "static-routes";
		    ngcliext:node-fmt "^$% @@$n";
		    cl:ignore-compare;
		}

		leaf id {
		    type uint32;
		    description
			"Numeric VRF table ID. " +
			"The value 0 is used by default tables";
		    ngcliext:node-fmt "^$% @@$n";
		    default 0;
		}

		container ipv4-routes {
		    description
			"List of IPv4 routes by destination prefix.";

		    list route {
			key "destination-prefix";
			description
			    "Routes are index by their destination.";

			ngcliext:context "static-routes";
			ngcliext:node-fmt "^route @{destination-prefix}$";
			ngcliext:pre-children-op "push";

			leaf destination-prefix {
			    type inet:ipv4-prefix;
			    description
				"IPv4 destination prefix";
			}

			leaf description {
			    type ngcom:description-63;
			    description
				"A description of the route.";
			    ngcliext:context "static-routes";
			    ngcliext:node-fmt "^$% @@$n";
			    cl:ignore-compare;
			}

			leaf priority {
			    type uint8;
			    description
				"Administrative distance
				preference.";
			    ngcliext:context "static-routes";
			    ngcliext:node-fmt "^$% @@$n";
			}

			leaf dataplane-only {
			    type empty;
			    description
				"FIB exclusive entry.";
			    ngcliext:context "static-routes";
			    ngcliext:node-fmt "^$%$n";
			}

			container next-hop {
			    description
				"Next-hop configuration.";

			    list hop {
				key "hop-id";
				description
				    "A list of next-hops.";

				ngcliext:context "static-routes";
				ngcliext:node-fmt "^next-hop @{hop-id} via ";

				leaf hop-id {
				    type uint32;
				    description
					"A unique identifier for
					 each next-hop.";
				}

				choice next-hop-choice {
				    case ipv4-address-case {
					leaf ipv4-address {
					    type inet:ipv4-address;
					    description
						"The next hop IPv4 address.";
					    ngcliext:context "static-routes";
					    ngcliext:node-fmt "@@%{if-name}%{next-hop-table-name}%{weight}%{resolve-host}%{resolve-attached}$n";
					}
				    }

				    case drop-case {
					leaf drop {
					    type boolean;
					    description
						"Drop the packet.";
					    ngcliext:context "static-routes";
					    ngcliext:node-op "bool";
					    ngcliext:node-fmt "|$%$n";
					}
				    }

				    case local-case {
					leaf local {
					    type boolean;
					    description
						"Receive the packet locally.";
					    ngcliext:context "static-routes";
					    ngcliext:node-op "bool";
					    ngcliext:node-fmt "|$%$n";
					}
				    }

				    case null-send-unreach-case {
					leaf null-send-unreach {
					    type boolean;
					    description
						"Drop packet with an
						 'unreachable' reply.";
					    ngcliext:context "static-routes";
					    ngcliext:node-op "bool";
					    ngcliext:node-fmt "|$%$n";
					}
				    }

				    case null-send-prohibit-case {
					leaf null-send-prohibit {
					    type boolean;
					    description
						"Drop packet with a
						 'prohibited' reply.";
					    ngcliext:context "static-routes";
					    ngcliext:node-op "bool";
					    ngcliext:node-fmt "|$%$n";
					}
				    }

				    case classify-table-name-case {
					leaf classify-table-name {
					    type string;
					    description
						"Use the given Classify Table
						 name as the next hop.";
					    ngcliext:context "static-routes";
					    ngcliext:node-fmt "classify @@$n";
					}
				    }
				}

				leaf if-name {
				    type ngcom:if-identifier-63;
				    description
					"The next hop interface name.";
				    ngcliext:context "static-routes";
				    ngcliext:sibling-fmt " @@";
				}

				leaf weight {
				    type uint8 {
					range "1..255";
				    }
				    description
					"Multipath route weight.";
				    ngcliext:context "static-routes";
				    ngcliext:sibling-fmt " $% @@";
				}

				leaf resolve-host {
				    type boolean;
				    description
					"Resolve host";
				    ngcliext:context "static-routes";
				    ngcliext:sibling-op "bool";
				    ngcliext:sibling-fmt "| resolve-via-host";
				}

				leaf resolve-attached {
				    type boolean;
				    description
					"Resolve attached";
				    ngcliext:context "static-routes";
				    ngcliext:sibling-op "bool";
				    ngcliext:sibling-fmt "| resolve-via-attached";
				}

				leaf next-hop-table-name {
				    type ngcom:rt-identifier-63;
				    description
					"The next hop route table name.";
				    ngcliext:context "static-routes";
				    ngcliext:sibling-fmt " next-hop-table @@";
				}
			    }
			}
		    }
		}

		container ipv6-routes {
		    description
			"List of IPv6 routes by destination prefix.";

		    list route {
			key "destination-prefix";
			description
			    "Routes are index by their destination.";

			ngcliext:context "static-routes";
			ngcliext:node-fmt "^route @{destination-prefix}$";
			ngcliext:pre-children-op "push";

			leaf destination-prefix {
			    type inet:ipv6-prefix;
			    description
				"IPv6 destination prefix";
			}

			leaf description {
			    type ngcom:description-63;
			    description
				"A description of the route.";
			    ngcliext:context "static-routes";
			    ngcliext:node-fmt "^$% @@$n";
			    cl:ignore-compare;
			}

			leaf priority {
			    type uint8;
			    description
				"Administrative distance
				preference.";
			    ngcliext:context "static-routes";
			    ngcliext:node-fmt "^$% @@$n";
			}

			leaf dataplane-only {
			    type empty;
			    description
				"FIB exclusive entry.";
			    ngcliext:context "static-routes";
			    ngcliext:node-fmt "^$%$n";
			}

			container next-hop {
			    description
				"Next-hop configuration.";

			    list hop {
				key "hop-id";
				description
				    "A list of next-hops.";

				ngcliext:context "static-routes";
				ngcliext:node-fmt "^next-hop @{hop-id} via ";

				leaf hop-id {
				    type uint32;
				    description
					"A unique identifier for
					 each next-hop.";
				}

				choice next-hop-choice {
				    case ipv6-address-case {
					leaf ipv6-address {
					    type inet:ipv6-address;
					    description
						"The next hop IPv6 address.";
					    ngcliext:context "static-routes";
					    ngcliext:node-fmt "@@%{if-name}%{next-hop-table-name}%{weight}%{resolve-host}%{resolve-attached}$n";
					}
				    }

				    case classify-table-name-case {
					leaf classify-table-name {
					    type string;
					    description
						"Use the given Classify Table
						name as the next hop.";
					    ngcliext:context "static-routes";
					    ngcliext:node-fmt "classify @@$n";
					}
				    }

				    case drop-case {
					leaf drop {
					    type boolean;
					    description
						"Drop the packet.";
					    ngcliext:context "static-routes";
					    ngcliext:node-op "bool";
					    ngcliext:node-fmt "|$%$n";
					}
				    }

				    case local-case {
					leaf local {
					    type boolean;
					    description
						"Receive the packet locally.";
					    ngcliext:context "static-routes";
					    ngcliext:node-op "bool";
					    ngcliext:node-fmt "|$%$n";
					}
				    }

				    case null-send-unreach-case {
					leaf null-send-unreach {
					    type boolean;
					    description
						"Drop packet with an
						'unreachable' reply.";
					    ngcliext:context "static-routes";
					    ngcliext:node-op "bool";
					    ngcliext:node-fmt "|$%$n";
					}
				    }

				    case null-send-prohibit-case {
					leaf null-send-prohibit {
					    type boolean;
					    description
						"Drop packet with a
						'prohibited' reply.";
					    ngcliext:context "static-routes";
					    ngcliext:node-op "bool";
					    ngcliext:node-fmt "|$%$n";
					}
				    }
				}

				leaf if-name {
				    type ngcom:if-identifier-63;
				    description
					"The next hop interface name.";
				    ngcliext:context "static-routes";
				    ngcliext:sibling-fmt " @@";
				}

				leaf next-hop-table-name {
				    type string;
				    description
					"The next hop route table name.";
				    ngcliext:context "static-routes";
				    ngcliext:sibling-fmt " next-hop-table @@";
				}

				leaf weight {
				    type uint8 {
					range "1..255";
				    }
				    description
					"Multipath route weight.";
				    ngcliext:context "static-routes";
				    ngcliext:sibling-fmt " $% @@";
				}

				leaf resolve-host {
				    type boolean;
				    description
					"Resolve host";
				    ngcliext:context "static-routes";
				    ngcliext:sibling-op "bool";
				    ngcliext:sibling-fmt "| resolve-via-host";
				}

				leaf resolve-attached {
				    type boolean;
				    description
					"Resolve attached";
				    ngcliext:context "static-routes";
				    ngcliext:sibling-op "bool";
				    ngcliext:sibling-fmt "| resolve-via-attached";
				}
			    }
			}
		    }
		}
	    }
	}
    }

    container route-table-state {
	config "false";

	description
	    "Route Table define a set of static IPv4 and IPv6 routes.";

	container static-routes {
	    description
		"Static routes.";

	    list route-table {
		key "name";
		description
		    "Route table entries are indexed by their name.
		     Table names are unique across all address families.";

		leaf name {
		    type ngcom:rt-identifier-63;
		    description
			"The name of a Route Table.";
		}

		leaf description {
		    type string;
		    description
			"A description of the route table.";
		}

		leaf id {
		    type uint32;
		    description
			"Numeric VRF table ID" +
			"The value 0 is used by default tables";
		    default 0;
		}

		container ipv4-routes {
		    description
			"List of IPv4 routes by destination prefix.";

		    list route {
			key "destination-prefix";
			description
			    "Routes are index by their destination.";

			leaf destination-prefix {
			    type inet:ipv4-prefix;
			    description
				"IPv4 destination prefix";
			}

			leaf description {
			    type string;
			    description
				"A description of the route.";
			}

			leaf priority {
			    type uint8;
			    description
				"Administrative distance
				preference.";
			}

			leaf class {
			    type route-class;
			    description
				"Route class.";
			}

			container next-hop {
			    description
				"Next-hop configuration.";

			    list hop {
				key "hop-id";
				description
				    "A list of next-hops.";

				leaf hop-id {
				    type uint32;
				    description
					"A unique identifier for
					 each next-hop.";
				}

				leaf ipv4-address {
				    type inet:ipv4-address;
				    description
					"The next hop IPv4 address.";
				}

				leaf if-name {
				    type ngcom:if-identifier-63;
				    description
					"The next hop interface name.";
				}

				leaf next-hop-table-name {
				    type ngcom:rt-identifier-63;
				    description
					"The next hop route table name.";
				}

				leaf classify-table-name {
				    type string;
				    description
					"Use the given Classify Table
					 name as the next hop.";
				}

				leaf weight {
				    type uint8;
				    description
					"Multipath route weight.";
				}

				leaf drop {
				    type boolean;
				    description
					"Drop the packet.";
				}

				leaf local {
				    type boolean;
				    description
					"Receive the packet locally.";
				}

				leaf null-send-unreach {
				    type boolean;
				    description
					"Drop packet with an
					 'unreachable' reply.";
				}

				leaf null-send-prohibit {
				    type boolean;
				    description
					"Drop packet with a
					 'prohibited' reply.";
				}

				leaf resolve-host {
				    type boolean;
				    description
					"Resolve host";
				}

				leaf resolve-attached {
				    type boolean;
				    description
					"Resolve attached";
				}

			    }
			}

		    }
		}

		container ipv6-routes {
		    description
			"List of IPv6 routes by destination prefix.";

		    list route {
			key "destination-prefix";
			description
			    "Routes are index by their destination.";

			leaf destination-prefix {
			    type inet:ipv6-prefix;
			    description
				"IPv6 destination prefix";
			}

			leaf description {
			    type string;
			    description
				"A description of the route.";
			}

			leaf priority {
			    type uint8;
			    description
				"Administrative distance
				preference.";
			}

			leaf class {
			    type route-class;
			    description
				"Route class.";
			}

			container next-hop {
			    description
				"Next-hop configuration.";

			    list hop {
				key "hop-id";
				description
				    "A list of next-hops.";

				leaf hop-id {
				    type uint32;
				    description
					"A unique identifier for
					 each next-hop.";
				}

				leaf ipv6-address {
				    type inet:ipv6-address;
				    description
					"The next hop IPv6 address.";
				}

				leaf if-name {
				    type ngcom:if-identifier-63;
				    description
					"The next hop interface name.";
				}

				leaf next-hop-table-name {
				    type string;
				    description
					"The next hop route table name.";
				}

				leaf classify-table-name {
				    type string;
				    description
					"Use the given Classify Table
					 name as the next hop.";
				}

				leaf weight {
				    type uint8;
				    description
					"Multipath route weight.";
				}

				leaf drop {
				    type boolean;
				    description
					"Drop the packet.";
				}

				leaf local {
				    type boolean;
				    description
					"Receive the packet locally.";
				}

				leaf null-send-unreach {
				    type boolean;
				    description
					"Drop packet with an
					 'unreachable' reply.";
				}

				leaf null-send-prohibit {
				    type boolean;
				    description
					"Drop packet with a
					 'prohibited' reply.";
				}

				leaf resolve-host {
				    type boolean;
				    description
					"Resolve host";
				}

				leaf resolve-attached {
				    type boolean;
				    description
					"Resolve attached";
				}
			    }
			}
		    }
		}
	    }
	}
    }
}
