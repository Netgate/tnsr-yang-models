module netgate-host-interface {

    yang-version 1.1;

    namespace "urn:netgate:xml:yang:netgate-host-interface";
    prefix "nghif";

    import clixon-lib {
	prefix "cl";
    }

    import ietf-inet-types {
	prefix "inet";
    }

    import ietf-yang-types {
	prefix "yang";
    }

    import netgate-cli-extensions {
	prefix "ngcliext";
    }

    import netgate-common {
	prefix "ngcom";
    }

    organization "Netgate";

    contact "Web: <http://www.netgate.com>";

    description
	"This YANG module provides a data model for host interfaces.

	 Copyright 2018-2026 Rubicon Communications, LLC.
	";

    revision 2026-06-01 {
	description
	    "TNSR Release 26.06.";
    }

    revision 2025-10-01 {
	description
	    "TNSR Release 25.10.";
    }

    revision 2025-02-01 {
	description
	    "TNSR Release 25.02.";
    }

    revision 2024-06-01 {
	description
	    "TNSR Release 24.06.";
    }

    revision 2023-02-15 {
	description
	    "TNSR Release 23.02.";
    }

    revision 2022-02-15 {
	description
	    "TNSR Release 22.02.";
    }

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-02-15 {
	description
	    "TNSR Release 19.02.";
    }

    revision 2018-08-23 {
	description
	    "Initial revision.";
    }

    container host-if-config {
	description
	    "Interface configuration parameters.";

	list interface {
	    key "name";

	    description
		"The list of configured host interfaces on the device.";

	    ngcliext:node-fmt "host interface @{name}$n";
	    ngcliext:pre-children-op "push";

	    leaf name {
		type string;
		description
		    "The name of the host interface.";
	    }

	    leaf description {
		type ngcom:description-63;
		description
		    "A textual description of the host interface.";
		ngcliext:node-fmt "^$% @@$n";
		cl:ignore-compare;
	    }

	    leaf enabled {
		type boolean;
		description
		    "This leaf contains the configured, desired state of
		     the interface.";
		ngcliext:node-op "bool";
		ngcliext:node-fmt "|^enable$n";
	    }

	    leaf mtu {
		type uint16 {
		    range "68..max";
		}
		units octets;
		description
		    "The size, in octets, of the largest packet that the
		     interface will send and receive.";
		ngcliext:node-fmt "^$% @@$n";
	    }

	    container ipv4 {
		description
		    "Parameters for the IPv4 address family.";

		ngcliext:parent-fmt "^ip";

		choice address-type {
		    case dhcp {
			container dhcp-client {

			    ngcliext:parent-fmt "$< dhcp-client";

			    leaf enabled {
				type boolean;
				description
				    "Enable DHCP client on the host
				     interface.";
				ngcliext:node-op "bool";
				ngcliext:node-fmt "|$< enable$n";
			    }

			    leaf hostname {
				type inet:domain-name;
				description
				    "Hostname";
				ngcliext:node-fmt "$< $% @@$n";
			    }
			}
		    }

		    case static {
			container address {

			    ngcliext:parent-fmt "$< address";

			    leaf-list ip {
				type inet:ipv4-prefix;
				description
				    "An IPv4 prefix on the host interface.";
				ngcliext:node-fmt "$< @@$n";
			    }
			}
		    }
		}
	    }

	    container ipv6 {
		description
		    "Parameters for the IPv6 address family.";

		ngcliext:parent-fmt "^ipv6";

		choice address-type {
		    case dhcp {
			container dhcp-client {

			    ngcliext:parent-fmt "$< dhcp-client";

			    leaf enabled {
				type boolean;
				description
				    "Enable DHCPv6 client on the host
				     interface.";
				ngcliext:node-op "bool";
				ngcliext:node-fmt "|$< enable$n";
			    }
			}
		    }

		    case static {
			container address {

			    ngcliext:parent-fmt "$< address";

			    leaf-list ip {
				type inet:ipv6-prefix;
				description
				    "An IPv6 prefix on the host interface.";
				ngcliext:node-fmt "$< @@$n";
			    }
			}
		    }
		}
	    }
	}
    }

    container host-if-state {
	config "false";

	description
	    "Interface configuration parameters.";

	list interface {
	    key "name";

	    description
		"The list of configured host interfaces on the device.";

	    leaf name {
		type string;
		description
		    "The name of the host interface.";
	    }

	    leaf description {
		type string;
		description
		    "A textual description of the host interface.";
	    }

	    leaf admin-status {
		type string;
		description
		    "The admin 'up' or 'down' status of the link.";
	    }

	    leaf link-status {
		type string;
		description
		    "The 'up' or 'down' status of the link.";
	    }

	    leaf link-mtu {
		type uint16 {
		    range "0 | 68..max";
		}
		units octets;
		description
		    "The size, in octets, of the largest packet that the
		     interface will send and receive. 0 indicates not known";
	    }

	    leaf mac-address {
		type yang:mac-address;
		description
		    "The Media Access Control (MAC) address of the
		    interface.";
	    }

	    container ipv4 {
		description
		    "Parameters for the IPv4 address family.";

		container address {
		    leaf-list ip {
			type inet:ipv4-prefix;
			description
			    "An IPv4 prefix on the host interface.";
		    }
		}
	    }

	    container ipv6 {
		description
		    "Parameters for the IPv6 address family.";

		container address {
		    leaf-list ip {
			type inet:ipv6-prefix;
			description
			    "An IPv6 prefix on the host interface.";
		    }
		}
	    }
	}
    }

    rpc hostif-dhclient-control {
        description
	    "Systemd service controls";

	input {
	    leaf name {
		type ngcom:host-if-name;
		mandatory true;
		description
		    "Name of an interface";
	    }
	    leaf ipversion {
		type ngcom:ip-address-family;
		mandatory true;
		description
		    "IP version";
	    }
	    leaf operation {
		type ngcom:service-operation;
		mandatory true;
		description
		    "The operation to perform";
	    }
	}
	output {
	    leaf stdout {
		type string;
	    }
	}
    }
}
