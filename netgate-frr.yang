module netgate-frr {

    yang-version 1.1;

    namespace "urn:netgate:xml:yang:netgate-frr";
    prefix "ngfrr";

    import clixon-lib {
	prefix "cl";
    }

    import ietf-inet-types {
	prefix "inet";
    }

    import netgate-cli-extensions {
	prefix "ngcliext";
    }

    import netgate-common {
	prefix "ngcom";
    }

    import netgate-frr-types {
	prefix "frr";
    }

    import netgate-route {
	prefix "ngrt";
    }

    organization "Netgate";

    contact "Web: <http://www.netgate.com>";

    description
	"This YANG module provides a Netgate-defined data-model
	 for FRR data.

	 Copyright 2017-2026 Rubicon Communications, LLC.
	 ";

    revision 2026-10-02 {
	description
	    "TNSR Release 26.10.";
    }

    revision 2026-10-01 {
	description
	    "TNSR Release 26.10.";
    }

    revision 2026-02-01 {
	description
	    "TNSR Release 26.02.";
    }

    revision 2025-06-01 {
	description
	    "TNSR Release 25.06.";
    }

    revision 2025-02-01 {
	description
	    "TNSR Release 25.02.";
    }

    revision 2024-06-01 {
	description
	    "TNSR Release 24.06.";
    }

    revision 2023-06-01 {
	description
	    "TNSR Release 23.06.";
    }

    revision 2023-02-16 {
	description
	    "TNSR Release 23.02.";
    }

    revision 2022-10-15 {
	description
	    "TNSR Release 22.10.";
    }

    revision 2022-02-15 {
	description
	    "TNSR Release 22.02.";
    }

    revision 2021-11-15 {
	description
	    "TNSR Release 21.11.";
    }

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-08-30 {
	description
	    "TNSR Release 19.08.";
    }

    revision 2019-05-30 {
	description
	    "TNSR Release 19.05.";
    }

    revision 2019-02-15 {
	description
	    "TNSR Release 19.02.";
    }

    revision 2019-01-15 {
	description
	    "Reorganize model to isolate routing service.";
    }

    revision 2017-11-01 {
	description
	    "Initial revision.";
    }


    typedef frr-show-request {
	type enumeration {
	    enum config-file {
		description
		    "FRR Configuration File";
	    }
	}
    }

    typedef ospf6-metric-type {
	type enumeration {
	    enum type-1 {
		description
		    "OSPF6 metric-type type-1.";
	    }

	    enum type-2 {
		description
		    "OSPF6 metric-type type-2.";
	    }
	}
    }

    typedef zebra-packet-send-recv {
	type enumeration {
	    enum send {
		description
		    "If specified, only sent packets are requested.";
	    }

	    enum recv {
		description
		    "If specified, only received  packets are requested.";
	    }
	}
    }

    typedef zebra-show-request {
	type enumeration {
	    enum config{
		description
		    "Show current running-config Zebra configurations.";
	    }
	}
    }

    grouping zebra-packet-send-recv {
	description
	    "Packet debug flags can specify a either a 'send' or
	     a 'recv' direction limiter, or if absent, both.";

	leaf direction {
	    type zebra-packet-send-recv;
	    description
		"Debug packets sent or received.
		Missing is both.";
	    ngcliext:node-fmt " @@";
	}
    }

    grouping zebra-packet-send-recv-detail {
	description
	    "Packet debug flags can specify a either a 'send' or
	     a 'recv' direction limiter, or if absent, both.
	     In addition a 'detail' flag may be requested.";

	leaf direction {
	    type zebra-packet-send-recv;
	    description
		"Debug packets sent or received.
		Missing is both.";
	    ngcliext:node-fmt " @@";
	}

	leaf detail {
	    type boolean;
	    description
		"Debug packets in detail.";
	    ngcliext:node-op "bool";
	    ngcliext:node-fmt "| $%";
	}
    }


    rpc frr-control {
	input {
	    leaf operation {
		mandatory true;
		type ngcom:service-operation;
		description
		    "One of the strings 'start', 'stop', 'restart',
		     or 'status'.";
	    }
	    leaf option {
		type string;
		description
		    "Option on operation";
	    }
	    leaf frr-service {
		type string;
	    }
	}
	output {
	    leaf stdout {
		type string;
	    }
	}
    }

    rpc frr-coredump {
	input {
	    leaf operation {
		mandatory true;
		type ngcom:service-op-enable-disable;
		description
		    "One of the strings 'enable', or 'disable'.";
	    }
	}
	output {
	    leaf stdout {
		type string;
	    }
	}
    }

    rpc frr-show {
	input {
	    leaf request {
		type frr-show-request;
		description
		    "An FRR show request type.";
	    }
	}
	output {
	    leaf stdout {
		type string;
	    }
	}
    }

    rpc zebra-show {
	input {
	    leaf request {
		type zebra-show-request;
		description
		    "A Zebra show request type.  Now only 'config' string.";
	    }
	}
	output {
	    leaf stdout {
		type string;
	    }
	}
    }

    rpc mgmtd-show {
	input {
	    leaf request {
		type zebra-show-request;
		description
		    "A mgmtd show request type.  Now only 'config' string.";
	    }
	}
	output {
	    leaf stdout {
		type string;
	    }
	}
    }

    augment "/ngrt:route-config/ngrt:dynamic" {

	leaf unmanaged {
	    type empty;
	    description
		"Indicates that dynamic routing configuration will be " +
		"manually maintained by the user. Mutually exclusive " +
		"with any other managed dynamic route configuration.";
	    ngcliext:node-fmt "route dynamic $%$n";
	}

	container snmp {
	    description
		"SNMP configuration options for all FRR protocols.";

	    leaf enable {
		type boolean;
		default false;
		description
		    "If true, SNMP is enabled for all FRR dynamic protocols.";
		ngcliext:node-op "bool";
		ngcliext:node-fmt "|route dynamic snmp $%$n";
	    }
	}

	container access-lists {
	    description
		"Table of Access Lists, indexed by name.  Each entry
		 contains a set of rules ordered by sequence number.";

	    list list {
		key "name";
		description
		    "Access List name.";

		ngcliext:node-fmt "route dynamic access-list @{name}$n";
		ngcliext:pre-children-op "push";

		leaf name {
		    type string;
		    mandatory true;
		    description
			"The Access List name as supplied by the developer.
			 It is a unique name used to identify this
			 set of Access List Rules.";
		}

		leaf remark {
		    type ngcom:description-63;
		    description
			"A user description of the Access List.";
		    ngcliext:node-fmt "^$% @@$n";
		}

		container rules {
		    description
			"Access List Rule Table ordered by sequence number.";

		    list rule {
			key "sequence";
			description
			    "A set of Access List Rules.";

			ngcliext:node-fmt "^sequence @{sequence} @{action} @{ip-prefix}$n";

			leaf sequence {
			    type uint32 {
				range "1..4294967295";
			    }
			    description
				"Rules are executed in increasing sequence
				 number.";
			}

			leaf action {
			    type frr:access-list-action;
			    description
				"One of the actions 'deny', 'permit'.";
			}

			leaf ip-prefix {
			    type inet:ip-prefix;
			    description
				"The IPv4 or IPv6 address and prefix.";
			}
		    }
		}
	    }
	}

	container prefix-lists {
	    description
		"Table of Prefix lists, indexed by name.  Each entry
		 contains a set of rules ordered by sequence number.";

	    list list {
		key "name";
		description
		    "Prefix List name.";

		ngcliext:node-fmt "route dynamic prefix-list @{name}$n";
		ngcliext:pre-children-op "push";

		leaf name {
		    type string;
		    mandatory true;
		    description
			"The Prefix List name as supplied by the developer.
			 It is a unique name used to identify this
			 set of Prefix List Rules.";
		}

		leaf description {
		    type ngcom:description-63;
		    description
			"A user description of the prefix list.";
		    ngcliext:node-fmt "^description @@$n";
		    cl:ignore-compare;
		}

		container rules {
		    description
			"Prefix List Rule Table ordered by sequence number.";

		    list rule {
			key "sequence";
			description
			    "A set of Prefix List Rules.";

			ngcliext:node-fmt "^sequence @{sequence} @{action} @{prefix}";
			ngcliext:post-node-fmt "$n";

			unique "prefix le-len ge-len";

			leaf sequence {
			    type uint32 {
				range "1..4294967295";
			    }
			    description
				"Rules are executed in increasing sequence
				 number.";
			}

			leaf action {
			    mandatory true;
			    type frr:prefix-list-action;
			    description
				"One of the actions 'deny', 'permit'.";
			}

			leaf prefix {
			    mandatory true;
			    type inet:ip-prefix;
			    description
				"The IPv4 or IPv6 address and prefix.";
			}

			leaf le-len {
			    type uint8;
			    default 0;
			    description
				"An upper bound on the prefix length.";
			    ngcliext:node-fmt " le @@";
			}

			leaf ge-len {
			    type uint8;
			    default 0;
			    description
				"A lower bound on the prefix length.";
			    ngcliext:node-fmt " ge @@";
			}
		    }
		}
	    }
	}

	container route-maps {
	    description
		"Table of Route Maps, indexed by name.	Each entry
		 contains a set of rules ordered by sequence number.";

	    list map {
		key "name";
		description
		    "Route Map entries indexed by name.";

		ngcliext:node-fmt "route dynamic route-map @{name}$n";
		ngcliext:pre-children-op "push";

		leaf name {
		    type string;
		    mandatory true;
		    description
			"The Route Map name as supplied by the
			 developer.  It is a unique name used to
			 identify a set of rules that belong together.
			 Each rule has a sequence number.";
		}

		leaf description {
		    type ngcom:description-63;
		    description
			"A user description of the Route Map.";
		    ngcliext:node-fmt "^$% @@$n";
		    cl:ignore-compare;
		}

		container rules {
		    description
			"Route Map Rule table.";

		    list rule {
			key "sequence";
			description
			    "The Route Map rule ordering sequence number.";

			ngcliext:node-fmt "^sequence @{sequence}$n";
			ngcliext:pre-children-op "push";

			leaf sequence {
			    type uint32 {
				range "1..65535";
			    }
			    description
				"Rules are applied in increasing
				 sequence order.";
			}

			leaf policy {
			    type frr:route-map-policy;
			    mandatory true;
			    description
				"One of the actions 'deny', 'permit'.";
			    ngcliext:node-fmt "^$% @@$n";
			}

			leaf description {
			    type ngcom:description-63;
			    description
				"A user description of the Route Map.";
			    ngcliext:node-fmt "^$% @@$n";
			    cl:ignore-compare;
			}

			container match {
			    description
				"A Rule may match based on various
				 different criteria.  More than one of
				 these may apply.";

			    ngcliext:parent-fmt "^$%";

			    leaf if-name {
				type string;
				description
				    "Match based on the name of an
				     interface.";
				ngcliext:node-fmt "$< interface @@$n";
			    }

			    leaf ip-address-access-list {
				type leafref {
				    path "/ngrt:route-config"
					+ "/ngrt:dynamic"
					+ "/ngfrr:access-lists/ngfrr:list"
					+ "/ngfrr:name";
				}
				description
				    "Match based on the name of an
				     Access List.";
				ngcliext:node-fmt "$< ip address access-list @@$n";
			    }

			    leaf ip-address-prefix-list {
				type leafref {
				    path "/ngrt:route-config"
					+ "/ngrt:dynamic"
					+ "/ngfrr:prefix-lists/ngfrr:list"
					+ "/ngfrr:name";
				}
				description
				    "Match based on the name of a
				    Prefix List.";
				ngcliext:node-fmt "$< ip address prefix-list @@$n";
			    }

			    leaf ip-next-hop-access-list {
				type leafref {
				    path "/ngrt:route-config"
					+ "/ngrt:dynamic"
					+ "/ngfrr:access-lists/ngfrr:list"
					+ "/ngfrr:name";
				}
				description
				    "Match based on the name of an
				     Access List.";
				ngcliext:node-fmt "$< ip next-hop access-list @@$n";
			    }

			    leaf ip-next-hop-ipv4-address {
				type inet:ipv4-address-no-zone;
				description
				    "Match an IPv4 address.";
				ngcliext:node-fmt "$< ip next-hop @@$n";
			    }

			    leaf ip-next-hop-prefix-list {
				type leafref {
				    path "/ngrt:route-config/ngrt:dynamic"
					+ "/ngfrr:prefix-lists/ngfrr:list"
					+ "/ngfrr:name";
				}
				description
				    "Match the prefixes specified by
				     the name of a Prefix List.";
				ngcliext:node-fmt "$< ip next-hop prefix-list @@$n";
			    }

			    leaf ipv6-address-access-list {
				type leafref {
				    path "/ngrt:route-config"
					+ "/ngrt:dynamic"
					+ "/ngfrr:access-lists/ngfrr:list"
					+ "/ngfrr:name";
				}
				description
				    "Match according to the name of an
				     Access List.";
				ngcliext:node-fmt "$< ipv6 address access-list @@$n";
			    }

			    leaf ipv6-address-prefix-list {
				type leafref {
				    path "/ngrt:route-config"
					+ "/ngrt:dynamic"
					+ "/ngfrr:prefix-lists"
					+ "/ngfrr:list"
					+ "/ngfrr:name";
				}
				description
				    "Match according to the name of a
				     Prefix List.";
				ngcliext:node-fmt "$< ipv6 address prefix-list @@$n";
			    }

			    leaf local-preference {
				type uint32;
				description
				    "The local preference value is matched.";
				ngcliext:node-fmt "$< $% @@$n";
			    }

			    container metric {
				description
				    "Settings for metric matching.";

				ngcliext:parent-fmt "$< $%";

				leaf value {
				    type uint32;
				    description
					"The metric value to be matched.";
				    ngcliext:node-fmt "$< @@$n";
				}
			    }

			    leaf origin {
				type frr:route-map-origin;
				description
				    "One of 'egp', 'igp',  or 'incomplete'.";
				ngcliext:node-fmt "$< origin @@$n";
			    }

			    leaf probability {
				type uint32;
				description
				    "Match a percentage of routes.";
				ngcliext:node-fmt "$< $% @@$n";
			    }

			    leaf source-protocol {
				type frr:route-map-source-protocol;
				description
				    "Match the route source protocol.
				     One of 'bgp', 'connected', 'kernel',
				     'ospf', 'ospf6', 'system'.";
				ngcliext:node-fmt "$< $% @@$n";
			    }

			    leaf tag {
				type uint32;
				description
				    "Match the router tag value.";
				ngcliext:node-fmt "$< $% @@$n";
			    }
			}

			container set {
			    description
				"Once a match is made, some 'set'
				 actions are specified.	 More than one
				 of these may apply.";

			    ngcliext:parent-fmt "^$%";

			    container aggregator {
				description
				    "Attributes about an aggregator.";

				ngcliext:node-fmt "$< $% as @{asn} ip address @{ip-address}$n";

				leaf asn {
				    type uint32;
				    description
					"Aggregator ASN.";
				}

				leaf ip-address {
				    type inet:ipv4-address-no-zone;
				    description
					"Aggregator IPv4 address.";
				}
			    }

			    leaf forwarding-address {
				type inet:ipv6-address;
				description
				    "IPv6 forwarding address.";
				ngcliext:node-fmt "$< $% @@$n";
			    }

			    container ip {
				description
				    "IP attributes to be set.";

				ngcliext:parent-fmt "$< $%";

				container next-hop {
				    description
					"IP next-hop attributes to be set.";

				    ngcliext:parent-fmt "$< $%";

				    leaf ipv4-address {
					type inet:ipv4-address-no-zone;
					description
					    "The next-hop is set to this
					     IPv4 address.";
					ngcliext:node-fmt "$< @@$n";
				    }

				    leaf unchanged {
					type boolean;
					description
					    "If true, the existing next hop
					     address is not modified.";
					ngcliext:node-op "bool";
					ngcliext:node-fmt "|$< $%$n";
				    }
				}
			    }

			    container ipv4 {
				description
				    "IPv4 attributes to be set.";

				ngcliext:parent-fmt "$< $%";

				container vpn {
				    description
					"IPv4 VPN settings.";

				    ngcliext:parent-fmt "$< $%";

				    container next-hop {
					description
					    "IPv4 VPN next-hop attributes
					     to be set.";

					ngcliext:parent-fmt "$< $%";

					leaf ipv4-address {
					    type inet:ipv4-address-no-zone;
					    description
						"The next-hop is set to
						 this IPv4 address.";
					    ngcliext:node-fmt "$< @@$n";
					}

					leaf ipv6-address {
					    type inet:ipv6-address;
					    description
						"The next-hop is set to
						 this IPv6 address.";
					    ngcliext:node-fmt "$< @@$n";
					}
				    }
				}
			    }

			    container ipv6 {
				description
				    "IPv6 attributes to be set.";

				ngcliext:parent-fmt "$< $%";

				container next-hop {
				    description
					"IPv6 next-hop attributes to
					 be set.";

				    ngcliext:parent-fmt "$< $%";

				    leaf global-ipv6-address {
					type inet:ipv6-address;
					description
					    "The next-hop global
					     address is set to this
					     IPv6 address.";
					ngcliext:node-fmt "$< global @@$n";
				    }

				    leaf local-ipv6-address {
					type inet:ipv6-address;
					description
					    "The next-hop local
					     address is set to this
					     IPv6 address.";
					ngcliext:node-fmt "$< local @@$n";
				    }

				    leaf prefer-global {
					type boolean;
					description
					    "If true, prefer the global
					     over the link-local if both
					     exist.";
					ngcliext:node-op "bool";
					ngcliext:node-fmt "|$< $%$n";
				    }
				}

				container vpn {
				    description
					"IPv6 VPN settings.";

				    ngcliext:parent-fmt "$< $%";

				    container next-hop {
					description
					    "IPv6 VPN next-hop attributes
					     to be set.";

					ngcliext:parent-fmt "$< $%";

					leaf ipv4-address {
					    type inet:ipv4-address-no-zone;
					    description
						"The next-hop is set to
						 this IPv4 address.";
					    ngcliext:node-fmt "$< @@$n";
					}

					leaf ipv6-address {
					    type inet:ipv6-address;
					    description
						"The next-hop is set to
						 this IPv6 address.";
					    ngcliext:node-fmt "$< @@$n";
					}
				    }
				}
			    }

			    leaf local-preference {
				type uint32;
				description
				    "Set the local preference attribute to
				     this value.";
				ngcliext:node-fmt "$< $% @@$n";
			    }

			    container metric {
				description
				    "Attributes for setting the metric.";

				ngcliext:parent-fmt "$< $%";

				leaf value {
				    type string {
					pattern "[+]?([0-9]|[1-9][0-9]+)";
				    }
				    description
					"Set the metric attribute to
					 this value.";
				    ngcliext:node-fmt "$< @@$n";
				}
			    }

			    container metric-type {
				description
				    "Attributes for setting the metric-type.";

				ngcliext:parent-fmt "$< $%";

				leaf type {
				    type ospf6-metric-type;
				    description
					"Set the metric-type attribute to
					 type-1 or type-2.";
				    ngcliext:node-fmt "$< @@$n";
				}
			    }

			    leaf origin {
				type frr:route-map-origin;
				description
				    "One of 'egp', 'igp',  or 'incomplete'.";
				ngcliext:node-fmt "$< $% @@$n";
			    }

			    container originator {
				description
				    "Originator ID information.";

				ngcliext:parent-fmt "$< originator-id";

				leaf ip-address {
				    type inet:ipv4-address-no-zone;
				    description
					"The IPv4 address of the originator.";
				    ngcliext:node-fmt "$< @@$n";
				}
			    }

			    leaf src-ip-address {
				type inet:ip-address-no-zone;
				description
				    "Set the src IP address to this
				     IPv4 or IPv6 address.";
				ngcliext:node-fmt "$< src @@$n";
			    }

			    leaf tag {
				type uint32;
				description
				    "Set the tag attribute to this value.";
				ngcliext:node-fmt "$< $% @@$n";
			    }

			    leaf weight {
				type uint32;
				description
				    "Set the weight attribute to this value.";
				ngcliext:node-fmt "$< $% @@$n";
			    }
			}

			container call {
			    description
				"Apply another Route Map entry much like a
				 traditional function call, expecting a
				 permit/deny response.";

			    ngcliext:parent-fmt "^$%";

			    leaf rt-map-name {
				type leafref {
				    path "/ngrt:route-config"
					+ "/ngrt:dynamic"
					+ "/ngfrr:route-maps"
					+ "/ngfrr:map/ngfrr:name";
				}
				description
				    "Call the named Route Map entry.";
				ngcliext:node-fmt "$< @@$n";
			    }
			}

			container exit {
			    description
				"As a final step in a Route Map, exit
				 conditions may be specified.";

			    ngcliext:parent-fmt "^on-match";

			    leaf on-match-next {
				type boolean;
				description
				    "Exit by coninuting to the next
				     Route Map.";
				ngcliext:node-op "bool";
				ngcliext:node-fmt "|$< next$n";
			    }

			    leaf on-match-goto {
				type uint32;
				description
				    "Jump to the next sequence number equal-to
				     or greater than this specified sequence
				     number within this same Route Map.";
				ngcliext:node-fmt "$< goto @@$n";
			    }
			}
		    }
		}
	    }
	}

	container manager {

	    ngcliext:node-fmt "route dynamic $%$n";
	    ngcliext:pre-children-op "push";

	    container global-options {
		description
		    "These are options that apply to the Zebra daemon.";

		container ipv4 {
		    description
			"Zebra global IPv4 options.";

		    container nht {
			description
			    "Zebra Nexthop Tracking options.";

			ngcliext:parent-fmt "$^ $%";

			leaf resolve-via-default {
			    type boolean;
			    default true;
			    description
				"Allow ipv4 nexthop tracking
				 to resolve via the default route.";

			    ngcliext:node-op "bool";
			    ngcliext:node-fmt "^no $< $%$n|";
			}
		    }
		}

		container ipv6 {
		    description
			"Zebra global IPv6 options.";

		    container nht {
			description
			    "Zebra Nexthop Tracking options.";

			ngcliext:parent-fmt "$^ $%";

			leaf resolve-via-default {
			    type boolean;
			    default true;
			    description
				"Allow ipv6 nexthop tracking
				 to resolve via the default route.";

			    ngcliext:node-op "bool";
			    ngcliext:node-fmt "^no $< $%$n|";
			}
		    }
		}

		container debug {
		    description
			"Zebra debug options.";

		    ngcliext:parent-fmt "^$%";

		    leaf events {
			type boolean;
			description
			    "If true, debug Zebra events.";
			ngcliext:node-op "bool";
			ngcliext:node-fmt "|$< $%$n";
		    }

		    leaf nht {
			type boolean;
			description
			    "If true, enable Zebra next hop tracking.";
			ngcliext:node-op "bool";
			ngcliext:node-fmt "|$< $%$n";
		    }

		    container kernel {
			presence
			    "If present, enable debugging between zebra
			     and the kernel.";

			ngcliext:node-fmt "$< $%";
			ngcliext:post-node-fmt "$n";

			container msgdump {
			    presence
				"If present dump raw netlink messages to
				 the kernel.  Without a modifier send or
				 receive flag, both sent and received
				 messages are printed.";

			    ngcliext:node-fmt "$< $%";

			    uses zebra-packet-send-recv;
			}
		    }

		    container packet {
			presence
			    "If present, enable Zebra packet debugging.";

			ngcliext:node-fmt "$< $%";
			ngcliext:post-node-fmt "$n";

			uses zebra-packet-send-recv-detail;
		    }

		    container rib {
			presence
			    "If present, enable Zebra RIB event debugging.";

			ngcliext:node-fmt "$< $%";
			ngcliext:post-node-fmt "$n";

			leaf detail {
			    type boolean;
			    description
				"If true, debug packets in detail.";
			    ngcliext:node-op "bool";
			    ngcliext:node-fmt "| $%";
			}
		    }
		}

		container log {
		    description
			"Zebra logging options.";

		    ngcliext:parent-fmt "^log";

		    container file {
			description
			    "Information used to log to a disk file.";

			ngcliext:node-fmt "$< $% @{filename}";
			ngcliext:post-node-fmt "$n";

			leaf filename {
			    type string;
			    description
				"The name of a log file.";
			}

			leaf level {
			    type frr:zebra-level;
			    description
				"One of the log-level names: alerts, critical,
				 debugging, emergencies, errors, informational,
				 notifications, or warnings.";
			    ngcliext:node-fmt " @@";
			}
		    }

		    container syslog {
			presence
			    "If present, log using syslog.";

			description
			    "Information used to log to syslog.";

			ngcliext:node-fmt "$< $%";
			ngcliext:post-node-fmt "$n";

			leaf level {
			    type frr:zebra-level;
			    description
				"One of the log-level names: alerts, critical,
				 debugging, emergencies, errors, informational,
				 notifications, or warnings.";
			    ngcliext:node-fmt " @@";
			}
		    }
		}

		leaf ptm {
		    type boolean;
		    default false;
		    description
			"If true, enable the Prescriptive Topology Manager.";
		}
	    }
	}
    }
}
