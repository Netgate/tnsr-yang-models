module netgate-ipfix {

    yang-version 1.1;

    namespace "urn:netgate:xml:yang:netgate-ipfix";
    prefix "ngipfix";

    import netgate-cli-extensions {
	prefix "ngcliext";
    }

    import netgate-common {
	prefix "ngcom";
    }

    import ietf-inet-types {
	prefix "inet";
    }

    import netgate-route-table {
	prefix "ngrttab";
    }

    organization "Netgate";

    contact "Web: <http://www.netgate.com>";

    description
	"This YANG module provides a Netgate-defined data-model
	 for IP Flow Information Export.

	 Copyright 2019-2024 Rubicon Communications, LLC.";

    revision 2025-06-01 {
	description
	    "TNSR Release 25.06.";
    }

    revision 2025-02-01 {
	description
	    "TNSR Release 25.02.";
    }

    revision 2023-11-01 {
	description
	    "TNSR Release 23.11.";
    }

    revision 2021-02-15 {
	description
	    "TNSR Release 21.02.";
    }

    revision 2020-10-15 {
	description
	    "TNSR Release 20.10.";
    }

    typedef ipfix-direction {
	type enumeration {
	    enum ingress {
		description
		    "Monitor incoming packets.";
	    }
	    enum egress {
		description
		    "Monitor outgoing packets.";
	    }
	    enum both {
		description
		    "Monitor incoming and outgoing packets.";
	    }
	}
    }

    typedef ipfix-filter-eid {
	type enumeration {
	    enum 60 {
		description
		    "ipVersion.";
	    }
	}
    }

    typedef ipfix-filter-ip-version-num {
	type enumeration {
	    enum 4 {
		description
		    "IPv4.";
	    }
	    enum 6 {
		description
		    "IPv6.";
	    }
	}
    }

    container ipfix-config {
	description
	    "Configuration for IP Flow Information Export. " +
	    "Data is structured the same as the ietf-ipfix-psamp model.";
	ngcliext:parent-fmt "ipfix";

	list cache {
	    key name;
	    description
		"Cache of the Monitoring Device.";
	    max-elements 1;
	    ngcliext:node-fmt "$< cache @{name}$n";
	    ngcliext:pre-children-op "push";

	    leaf name {
		type ngcom:identifier;
		description
		    "Name of the cache. " +
		    "Only one set of timeoutCache parameters is supported. " +
		    "Cache list is for compatibility with IETF model.";
	    }

	    container timeoutCache {
		description
		    "Flow expiration after active and idle timeout.";
		ngcliext:parent-fmt "^timeout-cache";

		leaf activeTimeout {
		    description
			"The time in seconds after which a flow is "+
			"expired even if packets are still received.";
		    type uint32 {
			range "1..max";
		    }
		    units seconds;
		    must "../idleTimeout" {
			error-message
			    "Both active and idle timer must be set";
		    }
		    ngcliext:node-fmt "$< active-timeout @@$n";
		}
		leaf idleTimeout {
		    description
			"The time in seconds after which a flow is "+
			"expired if no more packets mathing the flow "+
			"are received.";
		    type uint32;
		    units seconds;
		    must "../activeTimeout" {
			error-message
			    "Both active and idle timer must be set";
		    }
		    must "current() > ../activeTimeout" {
			error-message
			    "Idle timer must be greater than active timer";
		    }
		    ngcliext:node-fmt "$< idle-timeout @@$n";
		}
	    } /* timeoutCache */
	} /* cache */

	list exportingProcess {
	    description
		"Exporting Process of the Monitoring Device.";
	    key name;
	    max-elements 1;
	    ngcliext:node-fmt "$< exporter @{name}$n";
	    ngcliext:pre-children-op "push";

	    leaf name {
		type ngcom:identifier;
		description
		    "Name of exporting process.";
	    }

	    list destination {
		description
		    "List of export destinations.";
		key name;
		max-elements 1;

		leaf name {
		    type ngcom:identifier;
		    description
			"Name of the destination.";
		}

		container udpExporter {
		    description
			"UDP parameters.";

		    leaf destinationPort {
			type inet:port-number;
			description
			    "Port of the Collection Process.";
			ngcliext:sibling-fmt "@@";
		    }

		    leaf sourceIPAddress {
			type inet:ipv4-address-no-zone;
			description
			    "Source IP address used by the Exporting Process.";
			mandatory true;
			ngcliext:node-fmt "^source @@$n";
		    }

		    leaf destinationIPAddress {
			type inet:ipv4-address-no-zone;
			description
			    "IP address of the Collection Process.";
			mandatory true;
			ngcliext:node-fmt "^collector @@ port %{destinationPort}$n";
		    }

		    leaf maxPacketSize {
			type uint16 {
			    range "68..1450";
			}
			description
			    "Maximum size of IP packets sent to the Collector.";
			units octets;
			ngcliext:node-fmt "^pmtu @@$n";
		    }

		    leaf templateRefreshTimeout {
			type uint32;
			description
			    "Sets interval after which templates are resent.";
			units seconds;
			default 600;
			ngcliext:node-fmt "^template-interval @@$n";
		    }

		    leaf vrf {
			type ngrttab:route-table-id;
			description
			    "VRF to use to resolve collector address.";
			must "current() = 'default' or /ngrttab:route-table-config/ngrttab:static-routes/ngrttab:route-table[ngrttab:name=current()]" {
			    error-message "IPFIX collector VRF must refer to a valid VRF name";
			}
			ngcliext:node-fmt "^vrf @@$n";
		    }

		    leaf checksum {
			type boolean;
			description
			    "UDP checksum calculation enable flag.";
			ngcliext:node-fmt "^checksum @@$n";
		    }
		} /* udpExporter */
	    } /* destination */
	} /* exportingProcess */

	list observationPoint {
	    description
		"Observation Point of the Monitoring Device.";
	    key name;
	    leaf name {
		type ngcom:identifier;
		description
		    "Name of observation point.";
	    }
	    max-elements 1;
	    ngcliext:node-fmt "$< observation-point @{name}$n";
	    ngcliext:pre-children-op "push";

	    leaf observationDomainId {
		type enumeration {
		    enum 1 {
			description
			    "Only the value 1 is supported.";
		    }
		}
		description
		    "The Observation Domain ID for an Observation Point.";
		default 1;
	   }

	    leaf-list ifName {
		type ngcom:if-identifier-63;
		description
		    "Interface where packets are observed.";
		ngcliext:node-fmt "^interface @@$n";
	    }

	    leaf direction {
		type ipfix-direction;
		description
		    "Direction of packets.";
		default both;
		ngcliext:node-fmt "^$% @@$n";
	    }

	    leaf sample-rate {
		type uint32;
		description
		    "Number of packets to skip between sampling intervals.";
		default 0;
		ngcliext:node-fmt "^$% @@$n";
	    }

	    leaf sample-run-length {
		type uint32;
		description
		    "Number of packets to report in each interval.";
		default 1;
		ngcliext:node-fmt "^$% @@$n";
	    }

	} /* observationPoint */

	list selectionProcess {
	    key name;
	    description
		"Selection Process of the Monitoring Device.";
	    leaf name {
		type ngcom:identifier;
		description
		    "Name of selection process.";
	    }
	    max-elements 1;
	    ngcliext:node-fmt "$< selection-process @{name}$n";
	    ngcliext:pre-children-op "push";

	    list selector {
		key name;
		description
		    "Selectors that define action of selection process.";
		max-elements 1;

		leaf name {
		    type ngcom:identifier;
		    description
			"Name of selector.";
		    ngcliext:sibling-fmt "@@";
		}

		choice Method {
		    description
			"Packet selection method applied by the Selector.";
		    mandatory true;

		    case selectAll {
			leaf selectAll {
			    type empty;
			    description
				"Select all packets.";
			    ngcliext:node-fmt "^selector all$n";
			}
		    }
		    case filterMatch {
			container filterMatch {
			    description
				"Property match filtering.";
			    ngcliext:node-fmt "^selector %{name}$n";

			    leaf ieId {
				type ipfix-filter-eid;
				description
				    "Information Element identifier. " +
				    "Only value currently supported is " +
				    "ipVersion (60).";
			    }

			    leaf value {
				type ipfix-filter-ip-version-num;
				description
				    "Information Element value. " +
				    "Only values currently supported with " +
				    "ieId 60 are 4 and 6.";
			    }
			} /* container filterMatch */
		    } /* case filterMatch */
		} /* Method */
	    } /* selector */
	} /* selectionProcess */
    } /* ipfix-config */


    container ipfix-state {
        description
            "State information for IPFIX";
        config false;

        list observationPoint {
            key "name";
            description
              "Information about observation points";

            leaf name {
                type string;
                description
                  "Name of the observation point";
            }

            leaf observationDomainId {
                type uint32;
                description
                  "Observation domain ID";
            }

            leaf direction {
                type string;
                description
                  "Traffic flow direction (ingress, egress, or both)";
            }

            leaf sample-rate {
                type uint32;
                description
                  "Sampling rate configuration";
            }

            leaf sample-run-length {
                type uint32;
                description
                  "Sampling run length";
            }

            leaf-list ifName {
                type string;
                description
                  "Interface name";
            }
        }
    }
}
