module netgate-router {

    namespace "urn:netgate:xml:yang:netgate-router";
    prefix "ngr";

    import ietf-inet-types {
        prefix "inet";
    }

    import ietf-yang-types {
        prefix "yang";
    }

    import ietf-netconf-acm {
        prefix "nacm";
    }

    import netgate-acl {
        prefix "ngacl";
    }

    import netgate-bfd {
        prefix "ngbfd";
    }

    import netgate-frr {
        prefix "ngfrr";
    }

    import netgate-gre {
        prefix "nggre";
    }

    import netgate-host-interface {
        prefix "nghostif";
    }

    import netgate-host {
        prefix "nghost";
    }

    import netgate-http {
        prefix "nghttp";
    }

    import netgate-interface {
        prefix "ngif";
    }

    import netgate-ipsec {
        prefix "ngipsec";
    }

    import netgate-kea {
        prefix "ngkea";
    }

    import netgate-lldp {
        prefix "nglldp";
    }

    import netgate-macip {
        prefix "ngmacip";
    }

    import netgate-map {
        prefix "ngmap";
    }

    import netgate-master {
        prefix "ngmaster";
    }

    import netgate-nat {
        prefix "ngnat";
    }

    import netgate-neighbor {
        prefix "ngneigh";
    }

    import netgate-ntp {
        prefix "ngntp";
    }

    /*
    import netgate-ospf {
        prefix "ngospf";
    }
    */

    import netgate-package {
        prefix "ngpkg";
    }

    import netgate-pki {
        prefix "ngpki";
    }

    import netgate-route-table {
        prefix "ngrttbl";
    }

    import netgate-route {
        prefix "ngrt";
    }

    import netgate-span {
        prefix "ngspan";
    }

    import netgate-sysctl {
        prefix "ngsysctl";
    }

    import netgate-system {
        prefix "ngsys";
    }

    import netgate-dataplane {
        prefix "ngdataplane";
    }

    import netgate-unbound {
        prefix "ngunb";
    }

    import netgate-vxlan {
        prefix "ngvxlan";
    }

    organization "Netgate";

    contact "Web: <http://www.netgate.com>";

    description
        "This YANG module provides the top-level structure for all
         the components of a Netgate router.

         Copyright 2016-2019 Rubicon Communications, LLC.
        ";

    revision 2019-05-30 {
	description
	    "TNSR Release 19.05.";
    }

    revision 2019-02-15 {
	description
	    "TNSR Release 19.02.";
    }

    revision 2016-11-22 {
        description
            "Initial revision.";
    }

}
