module netgate-master {

    yang-version 1.1;

    namespace "urn:netgate:xml:yang:netgate-master";
    prefix "ngmaster";

    import netgate-common {
	prefix "ngcom";
    }

    organization "Netgate";

    contact "Web: <http://www.netgate.com>";

    description
        "Definitions of master data and operations.
	 Copyright 2019-2020 Rubicon Communications, LLC.
	 All rights reserved.";

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-05-30 {
	description
	    "TNSR Release 19.05.";
    }

    revision 2019-03-25 {
	description
	    "TNSR Release 19.02.";
    }


    typedef show-cli-option {
	type enumeration {
	    enum list-plugins {
		description
		    "Request a list of plugins.";
	    }
	    enum list-all-modules {
		description
		    "Request a list of all modules.";
	    }
	    enum list-cli-modules {
		description
		    "Request a list of modules that have CLI configuration
		     commands.";
	    }
	    enum get-commands {
		description
		    "Request the CLI commands for a given database.";
	    }
	}
    }


    rpc backend-coredump {
	input {
	    leaf operation {
		type ngcom:service-op-enable-disable;
		mandatory true;
		description
		    "One of the strings 'enable' or 'disable'.";
	    }
	}
	output {
	    leaf stdout {
		type string;
	    }
	}
    }

    rpc cli-show-cli {
	input {
	    leaf operation {
		type show-cli-option;
		mandatory true;
		description
		    "One of the operations 'list-plugins', 'list-modules',
		     or 'get-commands'.";
	    }
	    leaf database {
		type ngcom:database-name;
		description
		    "For 'get-commands', one of the database names 'running',
		     'candidate', or 'startup'.";
	    }
	    leaf module {
		type string {
		    length "1..63";
		}
		description
		    "For 'get-commands', and when set, the generated
		     CLI commands are limited to the given module.";
	    }
	    leaf indent {
		type boolean;
		description
		    "For 'get-commands', and if true, the generated CLI
		     commands will be indented.";
	    }
	}
	output {
	    leaf stdout {
		type string;
		description
		    "The generated CLI commands.";
	    }
	    container plugins {
		list plugin {
		    key name;
		    leaf name {
			type string;
		    }
		    leaf brief {
			type string;
		    }
		}
	    }
	    container modules {
		list module {
		    key name;
		    leaf name {
			type string;
		    }
		    leaf xml-root {
			type string;
		    }
		}
	    }
	}
    }

    rpc restconf-coredump {
	input {
	    leaf operation {
		type ngcom:service-op-enable-disable;
		mandatory true;
		description
		    "One of the strings 'enable' or 'disable'.";
	    }
	}
	output {
	    leaf stdout {
		type string;
	    }
	}
    }

}
