module netgate-http {

    yang-version 1.1;

    namespace "urn:ietf:params:xml:ns:yang:netgate-http";
    prefix "nghttp";

    import netgate-cli-extensions {
	prefix "ngcliext";
    }

    import netgate-common {
	prefix "ngcom";
    }

    organization "Netgate";

    contact "Web: <http://www.netgate.com>";

    description
	"This YANG module provides a data-model for the HTTP daemon.

	 Copyright 2018-2020 Rubicon Communications, LLC.
	";

    revision 2021-02-15 {
	description
	    "TNSR Release 21.02.";
    }

    revision 2020-06-15 {
	description
	    "TNSR Release 20.06.";
    }

    revision 2020-02-15 {
	description
	    "TNSR Release 20.02.";
    }

    revision 2019-05-30 {
	description
	    "TNSR Release 19.05.";
    }

    revision 2019-02-15 {
	description
	    "TNSR Release 19.02.";
    }

    revision 2018-07-04 {
	description
	    "Initial revision.";
    }

    typedef http-auth-type {
	type enumeration {
	    enum client-certificate {
		description
		    "TLS client certificate";
	    }
	    enum password {
		description
		    "PAM password auth";
	    }
	    enum none {
		description
		    "No authentication, no security.";
	    }
	}
	description
	    "Enumeration of HTTP authorization types.";
    }

    container http-config {
	description
	    "HTTP daemon configuration.";

	container restconf {
	    description
		"RESTconf configuration values.";

	    leaf enable {
		type boolean;
		description
		    "If true, RESTconf is enabled.";
		ngcliext:node-op "bool";
		ngcliext:node-fmt "|http enable restconf$n";
	    }
	}

	container dataplane {
	    description
		"Dataplane-specific parameters of HTTP server.";

	    leaf enable {
		type boolean;
		description
		    "If true, HTTP server is enabled for dataplane
		    interfaces.";
		ngcliext:node-op "bool";
		ngcliext:node-fmt "|http dataplane enable$n";
	    }
	}

	container daemon {
	    description
		"HTTP Daemon configuration.";

	    ngcliext:node-fmt "http server$n";
	    ngcliext:pre-children-op "push";

	    container authentication {
		description
		    "Authentication configuration.";

		ngcliext:parent-fmt "^authentication";

		leaf auth-type {
		    type http-auth-type;
		    description
			"The authentication type.";
		    ngcliext:node-fmt "$< type @@$n";
		}

		leaf client-cert-ca {
		    type string;
		    description
			"Client certificate.";
		    ngcliext:node-fmt "$< client-certificate-ca @@$n";
		}
	    }

	    container encryption {
		description
		    "Encryption.";

		leaf server-certificate {
		    type string;
		    description
			"Server certificate.";
		    ngcliext:node-fmt "^server certificate @@$n";
		}
	    }
	}
    }

    rpc http-control {
	input {
	    leaf operation {
		type ngcom:service-operation;
		mandatory true;
		description
		    "One of the strings 'start', 'stop', 'restart',
		     or 'status'.";
	    }

	    leaf namespace {
		type ngcom:network-namespace;
		description
		    "Network namespace.";
	    }
	}
	output {
	    leaf stdout {
		type string;
	    }
	}
    }

    rpc http-coredump {
	input {
	    leaf operation {
		type ngcom:service-op-enable-disable;
		mandatory true;
		description
		    "One of the strings 'enable', or 'disable'.";
	    }

	    leaf namespace {
		type ngcom:network-namespace;
		description
		    "Network namespace.";
	    }
	}
	output {
	    leaf stdout {
		type string;
	    }
	}
    }

    rpc http-config-operation {
	input {
	    leaf request {
		type string;
		description
		    "The operation, 'get-config-file'.";
	    }
	    leaf param {
		type string;
		description
		    "An optional parameter.";
	    }
	}
	output {
	    leaf stdout {
		type string;
	    }
	}
    }
}
