module netgate-sysctl {

    yang-version 1.1;

    namespace "urn:netgate:xml:yang:netgate-sysctl";
    prefix "ngsysctl";

    import netgate-cli-extensions {
	prefix "ngcliext";
    }

    organization "Netgate";

    contact "Web: <http://www.netgate.com>";

    description
	"This YANG module provides a Netgate-defined data-model
	 for Linux Kernel sysctl parameters.

	 Copyright 2018-2020 Rubicon Communications, LLC.
	 ";

    revision 2024-02-01 {
	description
	    "TNSR Release 24.02.";
    }

    revision 2021-02-15 {
	description
	    "TNSR Release 21.02.";
    }

    revision 2020-06-15 {
	description
	    "TNSR Release 20.06.";
    }

    revision 2020-02-15 {
	description
	    "TNSR Release 20.02.";
    }

    revision 2019-02-15 {
	description
	    "TNSR Release 19.02.";
    }

    revision 2018-01-08 {
	description
	    "Initial revision.";
    }

    container sysctl-config {
	description
	    "Linux kernel sysctl parameters.";

	ngcliext:parent-fmt "sysctl";

	container vm {
	    description
		"VM sysctl parameters.";

	    ngcliext:parent-fmt "$< vm";

	    leaf nr_hugepages {
		type uint64;
		default 1024;
		description
		    "Number of huge pages.";
		ngcliext:node-fmt "$< $% @@$n";
	    }

	    leaf nr_overcommit_hugepages {
		type uint64;
		default 256;
		description
		    "Number of extra huge pages.";
		ngcliext:node-fmt "$< $% @@$n";
	    }

	    leaf max_map_count {
		type uint64;
		default 65530;
		description
		    "Maximum map count.";
		ngcliext:node-fmt "$< $% @@$n";
	    }
	}

	container kernel {
	    description
		"Kernel sysctl parameters.";

	    ngcliext:parent-fmt "$< $%";

	    leaf shmmax {
	        type uint64;
		default 2147483648;
		description
		    "Shared memory maximum.";
		ngcliext:node-fmt "$< $% @@$n";
	    }
	}
    }

    container sysctl-state {
	config "false";

	description
	    "Linux kernel sysctl parameters.";

	container vm {
	    description
		"VM sysctl parameters.";

	    leaf nr_hugepages {
		type uint64;
		description
		    "Number of huge pages.";
	    }

	    leaf nr_overcommit_hugepages {
		type uint64;
		description
		    "Number of extra huge pages.";
	    }

	    leaf max_map_count {
		type uint64;
		description
		    "Maximum map count.";
	    }
	}

	container kernel {
	    description
		"Kernel sysctl parameters.";

	    leaf shmmax {
	        type uint64;
		description
		    "Shared memory maximum.";
	    }
	}
    }

}
