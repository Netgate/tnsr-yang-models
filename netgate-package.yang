module netgate-package {

    yang-version 1.1;

    namespace "urn:netgate:xml:yang:netgate-package";
    prefix "ngpkg";

    import netgate-cli-extensions {
	prefix "ngcliext";
    }

    organization "Netgate";

    contact "Web: <http://www.netgate.com>";

    description
	"This YANG module provides a data model for network interfaces.

	 Copyright 2018-2020,2023,2025 Rubicon Communications, LLC.
	";

    revision 2025-10-01 {
	description
	    "TNSR Release 25.10.";
    }

    revision 2020-06-15 {
	description
	    "TNSR Release 20.06.";
    }

    revision 2020-02-15 {
	description
	    "TNSR Release 20.02.";
    }

    revision 2019-02-15 {
	description
	    "TNSR Release 19.02.";
    }

    revision 2025-06-02 {
	description
	    "TNSR Release 25.06.";
    }

    container package-config {
	description
	    "Package configuration.";

	ngcliext:parent-fmt "package";

	leaf auto-update-lists {
	    type boolean;
	    default false;
	    description
		"Automatically update package lists.";
	    ngcliext:node-op "bool";
	    ngcliext:node-fmt "|$< $%$n";
	}
    }

    // get information about packages
    rpc package-info {
        input {
	    leaf allow {
	        type string;
		description
		    "optional limitation to packages
		     [ available | installed | updates ]
		     if not specified then all packages ";
	    }
	    leaf glob {
	        type string;
		description
		    "a glob to specify which packages
		     if not specified then default is '*' (all)";
            }
	}
	output {
	    leaf result {
	        type string;
		description
		    "results of package info query";
	    }
        }
    }

    // install a package
    rpc package-install {
        input {
	    leaf glob {
	        type string;
		mandatory true;
		description
		    "a glob to specify which packages
		     if not specified then default is '*' (all)";
            }
	}
	output {
	    leaf result {
	        type string;
		description
		    "results of package installation";
	    }
        }
    }

    // reinstall a package
    rpc package-reinstall {
        input {
	    leaf glob {
	        type string;
		mandatory true;
		description
		    "a glob to specify which packages
		     there is no default";
            }
	}
	output {
	    leaf result {
	        type string;
		description
		    "results of package reinstallation";
	    }
        }
    }

    // clean package cache
    rpc package-cache-cleanup {
	output {
	    leaf result {
	        type string;
		description
		    "results of cache cleanup";
	    }
        }
    }

    // update package cache
    rpc package-update {
	output {
	    leaf result {
	        type string;
		description
		    "results of cache cleanup";
	    }
        }
    }

    // list packages
    rpc package-list {
        input {
	    leaf allow {
	        type string;
		description
		    "optional limitation to packages
		     [ available | installed | updates ]
		     if not specified then all packages ";
	    }
	    leaf glob {
	        type string;
		description
		    "a glob to specify which packages, if
		     not specified then default is '*' (all)";
            }
	}
	output {
	    leaf result {
	        type string;
		description
		    "results of package info query";
	    }
        }
    }

    rpc package-remove {
        input {
	    leaf glob {
	        type string;
		mandatory true;
		description
		    "a glob to specify which packages, 
		     for safety, there is no default.";
            }
	}
	output {
	    leaf result {
	        type string;
		description
		    "results of package operation";
	    }
        }
    }

    rpc package-search {
        input {
	    leaf term {
	        type string;
		mandatory true;
		description
		    "search term for query";
            }
	}
	output {
	    leaf result {
	        type string;
		description
		    "results of package operation";
	    }
        }
    }

    rpc package-upgrade {
	output {
	    leaf result {
	        type string;
		description
		    "results of package operation";
	    }
        }
    }

    notification netgate-upgrade-event {
	description "Package upgrade notification event.";
	leaf message {
		type string;
	}
    }
}
