module netgate-frr-types {

    yang-version 1.1;

    namespace "urn:netgate:xml:yang:netgate-frr-types";
    prefix "frr";

    organization "Netgate";

    contact "Web: <http://www.netgate.com>";

    description
	"This module contains data typedefs needded by FRR.

	 Copyright 2018-2020 Rubicon Communications, LLC.
	 ";

    revision 2020-06-15 {
	description
	    "TNSR Release 20.06.";
    }

    revision 2020-02-15 {
	description
	    "TNSR Release 20.02.";
    }

    revision 2019-08-30 {
	description
	    "TNSR Release 19.08.";
    }

    revision 2019-05-30 {
	description
	    "TNSR Release 19.05.";
    }

    typedef access-list-action {
	type enumeration {
	    enum deny {
		description
		"Deny";
	    }
	    enum permit {
		description
		"Permit";
	    }
	}
    }

    typedef as-path-policy {
	type enumeration {
	    enum deny {
		description
		"Deny";
	    }
	    enum permit {
		description
		"permit";
	    }
	}
    }

    typedef prefix-list-action {
	type enumeration {
	    enum deny {
		description
		"Deny";
	    }
	    enum permit {
		description
		"Permit";
	    }
	}
    }

    typedef route-map-policy {
	type enumeration {
	    enum deny {
		description
		"Deny";
	    }
	    enum permit {
		description
		"Permit";
	    }
	}
    }

    typedef route-map-origin {
	type enumeration {
	    enum egp {
		description
		"EGP";
	    }
	    enum igp {
		description
		"IGP";
	    }
	    enum incomplete {
		description
		"Incomplete";
	    }
	}
    }

    typedef route-map-source-protocol {
	type enumeration {
	    enum bgp {
		description
		"BGP";
	    }
	    enum connected {
		description
		"Connected";
	    }
	    enum kernel {
		description
		"Kernel";
	    }
	    enum ospf {
		description
		"OSPF";
	    }
	    enum ospf6 {
		description
		"OSPF6";
	    }
	    enum system {
		description
		"System";
	    }
	    enum isis {
		description
		"IS-IS";
	    }
	}
    }

    typedef zebra-level {
	type enumeration {
	    enum alerts {
		description
		"Log Level Alert.";
	    }
	    enum critical {
		description
		"Log Level Critical.";
	    }
	    enum debugging {
		description
		"Log Level Debugging";
	    }
	    enum emergencies {
		description
		"Log Level Emergency";
	    }
	    enum errors {
		description
		"Log Level Error";
	    }
	    enum informational {
		description
		"Log Level Information";
	    }
	    enum notifications {
		description
		"Log Level Notification";
	    }
	    enum warnings {
		description
		"Log Level Warning";
	    }
	}
    }
}
