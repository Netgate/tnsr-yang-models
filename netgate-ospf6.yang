module netgate-ospf6 {

    yang-version 1.1;

    namespace "urn:netgate:xml:yang:netgate-ospf6";
    prefix "ngospf6";

    import ietf-inet-types {
	prefix "inet";
    }

    import ietf-yang-types {
	prefix "yang";
    }

    import netgate-cli-extensions {
	prefix "ngcliext";
    }

    import netgate-common {
	prefix "ngcom";
    }

    import netgate-frr {
	prefix "ngfrr";
    }

    import netgate-route {
	prefix "ngrt";
    }

    organization "Netgate";

    contact "Web: <http://www.netgate.com>";

    description
	"This YANG module provides a Netgate-defined data-model
	 for OSPFv3 data.

	 Copyright 2019-2023, 2025 Rubicon Communications, LLC.
	 ";

    revision 2025-06-01 {
	description
	    "TNSR Release 25.06.";
    }

    revision 2023-11-01 {
	description
	    "TNSR Release 23.11.";
    }

    revision 2023-02-01 {
	description
	    "TNSR Release 23.02.";
    }

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-12-15 {
	description
	    "TNSR Release 19.12.";
    }

    typedef ospf6-vrf-id {
	type ngcom:host-if-name;
    }

    typedef ospf6-area-id {
	type union {
	    type uint32;
	    type yang:dotted-quad;
	}
    }

    typedef ospf6-redistribution {
	type enumeration {
	    enum bgp {
		description
		    "BGP";
	    }
	    enum connected {
		description
		    "Connected";
	    }
	    enum kernel {
		description
		    "Kernel";
	    }
	    enum isis {
		description
		    "IS-IS";
	    }
	}
    }

    typedef ospf6-network-type {
	type enumeration {
	    enum broadcast {
		description
		    "Broadcast multi-access network.";
	    }

	    enum point-to-point {
		description
		    "Point-to-point network.";
	    }
	}
    }

    typedef ospf6-dead-interval {
	type uint16 {
	    range "1..65535";
	}
    }

    typedef ospf6-message-send-recv {
	type enumeration {
	    enum send {
		description
		    "If specified, only sent packets are requested.";
	    }

	    enum recv {
		description
		    "If specified, only received  packets are requested.";
	    }
	}
    }

    typedef ospf6-debug-neighbor-option {
	type enumeration {
	    enum event {
		description
		    "Debug OSPF6 neighbor events.";
	    }

	    enum state {
		description
		    "Debug OSPF6 neighbor state changes.";
	    }
	}
    }

    typedef ospf6-show-request {
	type enumeration {
	    enum config{
		description
		    "Show current running-config OSPF6 configurations.";
	    }

	    enum area {
		description
		    "Show area information.";
	    }

	    enum border-routers {
		description
		    "Show all the ABR's and ASBR's.";
	    }

	    enum database {
		description
		    "Database summary.";
	    }

	    enum default {
		description
		    "Show default information.";
	    }

	    enum interface {
		description
		    "Interface information.";
	    }

	    enum linkstate {
		description
		    "Linkstate information.";
	    }

	    enum neighbor {
		description
		    "Neighbor list.";
	    }

	    enum neighbor-detail {
		description
		    "Neighbor detailed list.";
	    }

	    enum route-table {
		description
		    "OSPF routing table.";
	    }

	    enum spf {
		description
		    "SPF Information.";
	    }
	}
    }

    typedef ospf6-show-parameter {
	type inet:ipv4-address-no-zone;
    }

    grouping ospf6-message-send-recv {
	description
	    "Packet debug flags can specify a either a 'send' or
	     a 'recv' direction limiter, or if absent, both.";

	leaf direction {
	    type ospf6-message-send-recv;
	    description
		"Debug packets sent or received.
		 Missing is both.";
	    ngcliext:child-fmt " @@";
	}
    }

    grouping ospf6-debug-lsa-options {
	description
	    "LSA debug detail options.";

	leaf no-options {
	    type boolean;
	    description
		"If true, debug the LSA without options.";
	    ngcliext:node-op "bool";
	    ngcliext:node-fmt "|$<$n";
	}

	leaf examine {
	    type boolean;
	    description
		"Print LSAs.";
	    ngcliext:node-op "bool";
	    ngcliext:node-fmt "|$< $%$n";
	}

	leaf flooding {
	    type boolean;
	    description
		"Print LSA's internal information.";
	    ngcliext:node-op "bool";
	    ngcliext:node-fmt "|$< $%$n";
	}

	leaf originate {
	    type boolean;
	    description
		"Print LSA details.";
	    ngcliext:node-op "bool";
	    ngcliext:node-fmt "|$< $%$n";
	}
    }

    rpc ospf6-show {
	input {
	    leaf vrf-id {
		type ospf6-vrf-id;
		default "default";
		description
		    "Each router is identified using the name of
		     a VRF, or the word 'default'.";
	    }
	    leaf request {
		type ospf6-show-request;
		description
		    "An OSPF show request type.";

	    }
	    leaf param {
		type ospf6-show-parameter;
		description
		    "An additional parameter string.";
	    }
	}
	output {
	    leaf stdout {
		type string;
	    }
	}
    }

    augment "/ngrt:route-config/ngrt:dynamic" {

	container ospf6 {

	    ngcliext:node-fmt "route dynamic ospf6$n";
	    ngcliext:pre-children-op "push";

	    container global-options {
		description
		    "These are options that apply to the OSPF6 Server or
		     to all OSPF6 Router configurations.";

		container debug {
		    description
			"OSPF6 debug configurations.";

		    ngcliext:parent-fmt "^$%";

		    leaf abr {
			type boolean;
			description
			    "Debug ABR.";
			ngcliext:node-op "bool";
			ngcliext:node-fmt "|$< $%$n";
		    }

		    leaf asbr {
			type boolean;
			description
			    "Debug ASBR.";
			ngcliext:node-op "bool";
			ngcliext:node-fmt "|$< $%$n";
		    }

		    container border-routers {
			description
			    "Debug border routers by area or router id.";

			ngcliext:parent-fmt "$< $%";

			leaf area-id {
			    type yang:dotted-quad;
			    description
				"Debug the border-routers with the
				 given area-id.";
			    ngcliext:node-fmt "$< area @@$n";
			}

			leaf router-id {
			    type yang:dotted-quad;
			    description
				"Debug the border-routers with the
				 given router-id.";
			    ngcliext:node-fmt "$< router @@$n";
			}
		    }

		    leaf flooding {
			type boolean;
			description
			    "Debug flooding.";
			ngcliext:node-op "bool";
			ngcliext:node-fmt "|$< $%$n";
		    }

		    leaf interface {
			type boolean;
			description
			    "Debug interfaces.";
			ngcliext:node-op "bool";
			ngcliext:node-fmt "|$< $%$n";
		    }

		    container lsa {
			description
			    "Debug OSPF link state advertisement";

			ngcliext:parent-fmt "$< $%";

			container as-external {
			    description
				"Debug AS-external LSAs.";

			    ngcliext:parent-fmt "$< $%";

			    uses ospf6-debug-lsa-options;
			}

			container inter-prefix {
			    description
				"Debug inter-area-prefix LSAs.";

			    ngcliext:parent-fmt "$< $%";

			    uses ospf6-debug-lsa-options;
			}

			container inter-router {
			    description
				"Debug inter-router LSAs.";

			    ngcliext:parent-fmt "$< $%";

			    uses ospf6-debug-lsa-options;
			}

			container intra-prefix {
			    description
				"Debug intra-area-prefix LSAs.";

			    ngcliext:parent-fmt "$< $%";

			    uses ospf6-debug-lsa-options;
			}

			container link {
			    description
				"Debug link LSAs.";

			    ngcliext:parent-fmt "$< $%";

			    uses ospf6-debug-lsa-options;
			}

			container network {
			    description
				"Debug network LSAs.";

			    ngcliext:parent-fmt "$< $%";

			    uses ospf6-debug-lsa-options;
			}

			container router {
			    description
				"Debug router LSAs.";

			    ngcliext:parent-fmt "$< $%";

			    uses ospf6-debug-lsa-options;
			}

			container unknown {
			    presence
				"If present, debug unknown LSAs.";

			    ngcliext:parent-fmt "$< $%";

			    uses ospf6-debug-lsa-options;
			}
		    }

		    container message {
			description
			    "Debug OSPF6 messages.";

			ngcliext:parent-fmt "$< $%";

			container dbdesc {
			    presence
				"If present, debug database
				 description packets.";

			    ngcliext:node-fmt "$< dd${direction}$n";

			    uses ospf6-message-send-recv;
			}

			container hello {
			    presence
				"If present, debug hello packets.";

			    ngcliext:node-fmt "$< $%${direction}$n";

			    uses ospf6-message-send-recv;
			}

			container ls-ack {
			    presence
				"If present, debug link state ACK packets.";

			    ngcliext:node-fmt "$< $%${direction}$n";

			    uses ospf6-message-send-recv;
			}

			container ls-request {
			    presence
				"If present, debug link state request
				 packets.";

			    ngcliext:node-fmt "$< $%${direction}$n";

			    uses ospf6-message-send-recv;
			}

			container ls-update {
			    presence
				"If present, debug ls-update packets.";

			    ngcliext:node-fmt "$< $%${direction}$n";

			    uses ospf6-message-send-recv;
			}

			container unknown {
			    presence
				"If present, debug unknown packets.";

			    ngcliext:node-fmt "$< $%${direction}$n";

			    uses ospf6-message-send-recv;
			}
		    }

		    container neighbor {
			presence
			    "If present, debug neighbors.";

			ngcliext:node-fmt "$< $%${option}$n";

			leaf option {
			    type ospf6-debug-neighbor-option;
			    description
				"Debug only 'event' or 'state' changes.";
			    ngcliext:child-fmt " @@";
			}
		    }

		    container route {
			description
			    "Debug OSPF6 routes.";

			ngcliext:parent-fmt "$< $%";

			leaf inter-area {
			    type boolean;
			    description
				"Debug inter-area route calculation.";
			    ngcliext:node-op "bool";
			    ngcliext:node-fmt "|$< $%$n";
			}

			leaf intra-area {
			    type boolean;
			    description
				"Debug intra-area route calculation.";
			    ngcliext:node-op "bool";
			    ngcliext:node-fmt "|$< $%$n";
			}

			leaf memory {
			    type boolean;
			    description
				"Debug route memory use.";
			    ngcliext:node-op "bool";
			    ngcliext:node-fmt "|$< $%$n";
			}

			leaf table {
			    type boolean;
			    description
				"Debug route table calculation.";
			    ngcliext:node-op "bool";
			    ngcliext:node-fmt "|$< $%$n";
			}
		    }

		    container spf {
			description
			    "Debug OSPF6 SPF calculation.";

			ngcliext:parent-fmt "$< $%";

			leaf database {
			    type boolean;
			    description
				"Log number of LSAs at SPF calculation time.";
			    ngcliext:node-op "bool";
			    ngcliext:node-fmt "|$< $%$n";
			}

			leaf process {
			    type boolean;
			    description
				"Debug SPF process in detail.";
			    ngcliext:node-op "bool";
			    ngcliext:node-fmt "|$< $%$n";
			}

			leaf time {
			    type boolean;
			    description
				"Measure time take by SPF calculations.";
			    ngcliext:node-op "bool";
			    ngcliext:node-fmt "|$< $%$n";
			}
		    }

		    container zebra {
			description
			    "Debug OSPF6 Zebra messages.";

			ngcliext:parent-fmt "$< $%";

			container messages {
			    presence
				"If present, debug Zebra messages.";

			    ngcliext:node-fmt "$< ${direction}$n";

			    uses ospf6-message-send-recv;
			}
		    }
		}

		leaf enable {
		    type boolean;
		    default false;
		    description
			"If true, the OSPF6 Daemon is enabled.";
		    ngcliext:node-op "bool";
		    ngcliext:node-fmt "|^$%$n";
		    must "current() = 'false' or not(../../../ngfrr:unmanaged)" {
			error-message
			    "OSPF6 configuration is not compatible " +
			    "with unmanaged dynamic routing configuration.";
		    }
		}
	    }

	    container interfaces {
		description
		    "OSPF6 configuration informataion for interfaces
		     includes enablement, cost, and timing data.";

		list if {
		    key if-name;

		    ngcliext:node-fmt "^interface @{if-name}$n";
		    ngcliext:pre-children-op "push";

		    leaf if-name {
			type string;
			description
			    "The interface with OSPF6 enabled on it.";
		    }

		    container advertise {
			description
			    "Advertising options.";

			ngcliext:parent-fmt "^$%";

			leaf prefix-list-name {
			    type leafref {
				path "/ngrt:route-config"
				    + "/ngrt:dynamic"
				    + "/ngfrr:prefix-lists/ngfrr:list"
				    + "/ngfrr:name";
			    }
			    description
				"Use prefix-list as a filter.";
			    ngcliext:node-fmt "$< prefix-list @@$n";
			}
		    }

		    container cost {
			description
			    "Interface costs.";

			ngcliext:parent-fmt "^$%";

			leaf outgoing {
			    type uint16 {
				range "1..65535";
			    }
			    description
				"The outgoing metric for this interface.";
			    ngcliext:node-fmt "$< $% @@$n";
			}
		    }

		    container dead-interval {
			description
			    "Interval time after which a neighbor is
			     declared dead.  The interval is a number of
			     seconds in the range [1..65535].";

			ngcliext:parent-fmt "^$%";

			leaf interval {
			    type uint16 {
				range "1..65535";
			    }
			    description
				"Interval time after which a neighbor
				 is declared dead.";
			    ngcliext:node-fmt "$< @@$n";
			}
		    }

		    container hello-interval {
			description
			    "The interval between hello packets.";

			ngcliext:parent-fmt "^$%";

			leaf interval {
			    type uint16 {
				range "1..65535";
			    }
			    description
				"The interval between hello packets,
				 in seconds, 1..65535.";
			    ngcliext:node-fmt "$< @@$n";
			}
		    }

		    leaf ifmtu {
			type uint16 {
			    range "1..65535";
			}
			description
			    "MTU parameter for an interface.";
			ngcliext:node-fmt "^mtu @@$n";
		    }

		    leaf instance-id {
			type uint16 {
			    range "0..255";
			}
			description
			    "Instance ID of the interface.";
			ngcliext:node-fmt "^$% @@$n";
		    }

		    leaf mtu-ignore {
			type boolean;
			description
			    "Disable MTU mismatch detection on this
			     interface";
			ngcliext:node-op "bool";
			ngcliext:node-fmt "|^$%$n";
		    }

		    container network {
			description
			    "Network parameters";

			ngcliext:parent-fmt "^$%";

			leaf type {
			    type ospf6-network-type;
			    description
				"OSPF6 Network type is one of 'broadcast',
				 or 'point-to-point'.";
			    ngcliext:node-fmt "$< @@$n";
			}
		    }

		    leaf passive {
			type boolean;
			description
			    "If true, the interface will be passive and
			     no adjacency will be formed.";
			ngcliext:node-op "bool";
			ngcliext:node-fmt "|^$%$n";
		    }

		    leaf priority {
			type uint8;
			description
			    "Router priority, 0..255.";
			ngcliext:node-fmt "^$% @@$n";
		    }

		    container retransmit {
			description
			    "Time in seconds between retransmitting lost
			     link state advertisements.";

			ngcliext:node-fmt "^retransmit-interval @{interval}$n";

			leaf interval {
			    type uint16 {
				range "1..65535";
			    }
			    description
				"Interval between retransmitting lost
				 LSAs, in seconds.";
			}
		    }

		    container transmit {
			description
			    "Link state transmit delay information.";

			ngcliext:node-fmt "^transmit-delay @{delay}$n";

			leaf delay {
			    type uint16 {
				range "1..3600";
			    }
			    description
				"The LSA transmit delay, 1..3600
				 in seconds.";
			}
		    }

		    leaf bfd {
			type boolean;
			description
			    "Bidirectional Forwarding Detection (BFD)
			     is enabled for this interface.";
			ngcliext:node-op "bool";
			ngcliext:node-fmt "|^$% enabled true$n";
		    }
		}
	    }

	    container routers {
		description
		    "Table of OSPF6 Router instances .";

		list router {
		    key vrf-id;

		    description
			"The router contains all information for one instance
			 of the OSPF6 protocol as supported by FRR.";

		    ngcliext:node-fmt "^server vrf @{vrf-id}$n";
		    ngcliext:pre-children-op "push";

		    leaf vrf-id {
			type ospf6-vrf-id;
			description
			    "Each router is identified using the name of
			     a VRF, or the word 'default'.";
		    }

		    container areas {
			description
			    "The OSPF6 protocol operates on independent
			     link state regions called 'areas'.";

			list area {
			    key area-id;

			    ngcliext:node-fmt "^$% @{area-id}$n";
			    ngcliext:pre-children-op "push";

			    leaf area-id {
				type ospf6-area-id;
				description
				    "Each area must have a unique ID
				     that takes the form of either a
				     dotted-quad or an unsigned 32-bit
				     number, interchangeably.  That
				     is, dotted-quad 0.0.0.1 is the
				     same as the unsigned number 1.";
			    }

			    container ranges {
				description
				    "Summarize intra-area paths from
				     speified area into one Type-3
				     Summary LSA announced to other areas.";

				list range {
				    key "prefix";

				    ngcliext:parent-fmt "^$% @{prefix}";

				    leaf prefix {
					type inet:ipv6-prefix;
					description
					    "Area range IPv6 prefix.";
				    }

				    container range-data {
					presence
					    "If present, hold range
					     data for the prefix.";

					ngcliext:parent-fmt "$<";
					ngcliext:node-op "test-set:@{not-advertise}@{cost}";
					ngcliext:node-fmt "$<$n|";

					leaf not-advertise {
					    type boolean;
					    description
						"If true, do not advertise
						 this prefix.";
					    ngcliext:node-op "bool";
					    ngcliext:node-fmt "|$< $%$n";
					}

					leaf cost {
					    type uint32 {
						range "0..16777215";
					    }
					    description
						"Cost metric for this range.";
					    ngcliext:node-fmt "$< $% @@$n";
					}
				    }
				}
			    }

			    container stub {
				presence
				    "If present, configure area as a stub.";

				ngcliext:node-fmt "^stub${no-summary}$n";

				leaf no-summary {
				    type boolean;
				    description
					"Do not inject inter-area routes
					 into stub.";
				    ngcliext:child-fmt " $%";
				}
			    }
			}
		    }

		    container auto-cost {

			ngcliext:parent-fmt "^$%";

			leaf reference-bandwidth {
			    type uint32 {
				range "1..4294967";
			    }
			    description
				"The reference bandwidth, 1..4294967,
				 in MBits/sec.";
			    ngcliext:node-fmt "$< $% @@$n";
			}
		    }

		    container default-information {
			description
			    "Control distribution of default route.";

			ngcliext:parent-fmt "^$%";

			container originate {
			    description
				"Distribute a default route.";

			    ngcliext:node-fmt "$< $%${always}${metric}${metric-type}${route-map}$n";

			    presence
				"When present, a default route will
				 be distributed.";

			    leaf always {
				type boolean;
				description
				    "Always advertise default route.";
				ngcliext:child-op "bool";
				ngcliext:child-fmt "| $%";
			    }

			    leaf metric {
				type uint32 {
				    range "0..16777214";
				}
				description
				    "Default OSPFv3 metric.";
				ngcliext:child-fmt " $% @@";
			    }

			    leaf metric-type {
				type uint32 {
				    range "1..2";
				}
				description
				    "Metric type for default routes.";
				ngcliext:child-fmt " $% @@";
			    }

			    leaf route-map {
				type leafref {
				    path "/ngrt:route-config"
					+ "/ngrt:dynamic"
					+ "/ngfrr:route-maps"
					+ "/ngfrr:map"
					+ "/ngfrr:name";
				}
				description
				    "Name of a route-map.";
				ngcliext:child-fmt " $% @@";
			    }
			}
		    }

		    container distance {
			description
			    "OSPF6 administrative distances for routes.";

			ngcliext:parent-fmt "^$%";

			leaf administrative {
			    type uint8 {
				range "1..255";
			    }
			    description
				"OSPF6 administrative distance.";
			    ngcliext:node-fmt "$< @@$n";
			}

			leaf external {
			    type uint8 {
				range "1..255";
			    }
			    description
				"OSPF6 administrative distance for external
				 routes.";
			    ngcliext:node-fmt "$< $% @@$n";
			}

			leaf inter-area {
			    type uint8 {
				range "1..255";
			    }
			    description
				"OSPF6 administrative distance for inter-area
				 routes.";
			    ngcliext:node-fmt "$< $% @@$n";
			}

			leaf intra-area {
			    type uint8 {
				range "1..255";
			    }
			    description
				"OSPF6 administrative distance for intra-area
				 routes.";
			    ngcliext:node-fmt "$< $% @@$n";
			}
		    }

		    container interfaces {
			description
			    "OSPF6 configuration informataion for
			     interfaces includes enablement,
			     cost and timing data.";

			list if {
			    key if-name;

			    ngcliext:node-fmt "^interface @{if-name} area @{area-id}$n";

			    leaf if-name {
				type string;
				description
				    "The interface with OSPF6 enabled
				    on it.";
			    }

			    leaf area-id {
				type ospf6-area-id;
				description
				    "The dotted-quad or uint32 area identifier.";
			    }
			}
		    }

		    container log-adjacency-changes {
			presence
			    "If present, changes in adjacency state
			     will be logged.";

			ngcliext:node-fmt "^$%${detail}$n";

			leaf detail {
			    type boolean;
			    description
				"If true, all state changes will be logged.";
			    ngcliext:child-op "bool";
			    ngcliext:child-fmt "| detail";
			}
		    }

		    container ospf6 {
			description
			    "OSPF6 attributes.";

			ngcliext:parent-fmt "^$%";

			leaf router-id {
			    type yang:dotted-quad;
			    description
				"The unique ID of this OSPF6 router as a
				 dotted-quad.";
			    ngcliext:node-fmt "$< $% @@$n";
			}
		    }

		    container redistributions {
			description
			    "Configure which route types from other protocols
			     should be distributed into OSPF6.";

			list redistribution {
			    key source;

			    ngcliext:parent-fmt "^redistribute @{source}";

			    leaf source {
				type ospf6-redistribution;
				description
				    "The source of routes that will be
				     distributed into OSPF6.";
			    }

			    container redistribution-data {
				presence
				    "If present, routes from this source will
				     be distributed into OSPF6.";

				ngcliext:node-fmt "$<${route-map}$n";

				leaf route-map {
				    type leafref {
					path "/ngrt:route-config"
					    + "/ngrt:dynamic"
					    + "/ngfrr:route-maps"
					    + "/ngfrr:map"
					    + "/ngfrr:name";
				    }
				    description
					"Route-map used to filter routes into
					 OSPF6.";
				    ngcliext:child-fmt " $% @@";
				}
			    }
			}
		    }

		    container stub-router {

			ngcliext:parent-fmt "^$%";

			leaf administrative {
			    type boolean;
			    description
				"If true, this router will be a stub.";
			    ngcliext:node-op "bool";
			    ngcliext:node-fmt "|$< $%$n";
			}
		    }

		    container timers {
			description
			    "OSPF6 timer configurations.";

			ngcliext:parent-fmt "^$%";

			container lsa {
			    description
				"OSPF6 LSA timer configurations.";

			    ngcliext:parent-fmt "$< $%";

			    leaf min-arrival {
				type uint32 {
				    range "0..600000";
				}
				description
				    "Mimimum delay in receiving new
				     versions of an LSA, in ms.";
				ngcliext:node-fmt "$< $% @@$n";
			    }
			}

			container throttle {
			    description
				"Throttle adaptive timer configurations.";

			    ngcliext:parent-fmt "$< $%";

			    container spf {
				description
				    "SPF timers.";

				ngcliext:parent-fmt "$< $%";

				leaf delay {
				    type uint32 {
					range "0..600000";
				    }
				    description
					"Delay from first received change until
					 SPF calculation, in ms.";
				    ngcliext:node-fmt "$< $% @@$n";
				}

				leaf initial-hold {
				    type uint32 {
					range "0..600000";
				    }
				    description
					"Initial hold time between consecutive
					 SPF calculation, in ms.";
				    ngcliext:node-fmt "$< $% @@$n";
				}

				leaf maximum-hold {
				    type uint32 {
					range "0..600000";
				    }
				    description
					"Maximum hold time, in ms.";
				    ngcliext:node-fmt "$< $% @@$n";
				}
			    }
			}
		    }
		}
	    }
	}
    }

    augment "/ngrt:route-state/ngrt:dynamic" {

	container ospf6 {

	    config "false";

	    container global-options {
		description
		    "These are options that apply to the OSPF6 Server or
		     to all OSPF6 Router configurations.";

		container debug {
		    description
			"OSPF6 debug configurations.";

		    leaf abr {
			type boolean;
			description
			    "Debug ABR.";
		    }

		    leaf asbr {
			type boolean;
			description
			    "Debug ASBR.";
		    }

		    container border-routers {
			description
			    "Debug border routers by area or router id.";

			leaf area-id {
			    type yang:dotted-quad;
			    description
				"Debug the border-routers with the
				 given area-id.";
			}

			leaf router-id {
			    type yang:dotted-quad;
			    description
				"Debug the border-routers with the
				 given router-id.";
			}
		    }

		    leaf flooding {
			type boolean;
			description
			    "Debug flooding.";
		    }

		    leaf interface {
			type boolean;
			description
			    "Debug interfaces.";
		    }

		    container lsa {
			description
			    "Debug OSPF link state advertisement";

			container as-external {
			    description
				"Debug AS-external LSAs.";

			    uses ospf6-debug-lsa-options;
			}

			container inter-prefix {
			    description
				"Debug inter-area-prefix LSAs.";

			    uses ospf6-debug-lsa-options;
			}

			container inter-router {
			    description
				"Debug inter-router LSAs.";

			    uses ospf6-debug-lsa-options;
			}

			container intra-prefix {
			    description
				"Debug intra-area-prefix LSAs.";

			    uses ospf6-debug-lsa-options;
			}

			container link {
			    description
				"Debug link LSAs.";

			    uses ospf6-debug-lsa-options;
			}

			container network {
			    description
				"Debug network LSAs.";

			    uses ospf6-debug-lsa-options;
			}

			container router {
			    description
				"Debug router LSAs.";

			    uses ospf6-debug-lsa-options;
			}

			container unknown {
			    presence
				"If present, debug unknown LSAs.";

			    uses ospf6-debug-lsa-options;
			}
		    }

		    container message {
			description
			    "Debug OSPF6 messages.";

			container dbdesc {
			    presence
				"If present, debug database
				 description packets.";

			    uses ospf6-message-send-recv;
			}

			container hello {
			    presence
				"If present, debug hello packets.";

			    uses ospf6-message-send-recv;
			}

			container ls-ack {
			    presence
				"If present, debug link state ACK packets.";

			    uses ospf6-message-send-recv;
			}

			container ls-request {
			    presence
				"If present, debug link state request
				 packets.";

			    uses ospf6-message-send-recv;
			}

			container ls-update {
			    presence
				"If present, debug ls-update packets.";

			    uses ospf6-message-send-recv;
			}

			container unknown {
			    presence
				"If present, debug unknown packets.";

			    uses ospf6-message-send-recv;
			}
		    }

		    container neighbor {
			presence
			    "If present, debug neighbors.";

			leaf option {
			    type ospf6-debug-neighbor-option;
			    description
				"Debug only 'event' or 'state' changes.";
			}
		    }

		    container route {
			description
			    "Debug OSPF6 routes.";

			leaf inter-area {
			    type boolean;
			    description
				"Debug inter-area route calculation.";
			}

			leaf intra-area {
			    type boolean;
			    description
				"Debug intra-area route calculation.";
			}

			leaf memory {
			    type boolean;
			    description
				"Debug route memory use.";
			}

			leaf table {
			    type boolean;
			    description
				"Debug route table calculation.";
			}
		    }

		    container spf {
			description
			    "Debug OSPF6 SPF calculation.";

			leaf database {
			    type boolean;
			    description
				"Log number of LSAs at SPF calculation time.";
			}

			leaf process {
			    type boolean;
			    description
				"Debug SPF process in detail.";
			}

			leaf time {
			    type boolean;
			    description
				"Measure time take by SPF calculations.";
			}
		    }

		    container zebra {
			description
			    "Debug OSPF6 Zebra messages.";

			container messages {
			    presence
				"If present, debug Zebra messages.";

			    uses ospf6-message-send-recv;
			}
		    }
		}

		leaf enable {
		    type boolean;
		    default false;
		    description
			"If true, the OSPF6 Daemon is enabled.";
		}
	    }

	    container interfaces {
		description
		    "OSPF6 configuration informataion for interfaces
		     includes enablement, cost, and timing data.";

		list if {
		    key if-name;

		    leaf if-name {
			type string;
			description
			    "The interface with OSPF6 enabled on it.";
		    }

		    container advertise {
			description
			    "Advertising options.";

			leaf prefix-list-name {
			    type string;
			    description
				"Use prefix-list as a filter.";
			}
		    }

		    container cost {
			description
			    "Interface costs.";

			leaf outgoing {
			    type uint16 {
				range "1..65535";
			    }
			    description
				"The outgoing metric for this interface.";
			}
		    }

		    container dead-interval {
			description
			    "Interval time after which a neighbor is
			     declared dead.  The interval is a number of
			     seconds in the range [1..65535].";

			leaf interval {
			    type uint16 {
				range "1..65535";
			    }
			    description
				"Interval time after which a neighbor
				 is declared dead.";
			}
		    }

		    container hello-interval {
			description
			    "The interval between hello packets.";

			leaf interval {
			    type uint16 {
				range "1..65535";
			    }
			    description
				"The interval between hello packets,
				 in seconds, 1..65535.";
			}
		    }

		    leaf ifmtu {
			type uint16 {
			    range "1..65535";
			}
			description
			    "MTU parameter for an interface.";
		    }

		    leaf instance-id {
			type uint16 {
			    range "0..255";
			}
			description
			    "Instance ID of the interface.";
		    }

		    leaf mtu-ignore {
			type boolean;
			description
			    "Disable MTU mismatch detection on this
			     interface";
		    }

		    container network {
			description
			    "Network parameters";

			leaf type {
			    type ospf6-network-type;
			    description
				"OSPF6 Network type is one of 'broadcast',
				 or 'point-to-point'.";
			}
		    }

		    leaf passive {
			type boolean;
			description
			    "If true, the interface will be passive and
			     no adjacency will be formed.";
		    }

		    leaf priority {
			type uint8;
			description
			    "Router priority, 0..255.";
		    }

		    container retransmit {
			description
			    "Time in seconds between retransmitting lost
			     link state advertisements.";

			leaf interval {
			    type uint16 {
				range "1..65535";
			    }
			    description
				"Interval between retransmitting lost
				 LSAs, in seconds.";
			}
		    }

		    container transmit {
			description
			    "Link state transmit delay information.";

			leaf delay {
			    type uint16 {
				range "1..3600";
			    }
			    description
				"The LSA transmit delay, 1..3600
				 in seconds.";
			}
		    }

		    leaf bfd {
			type boolean;
			description
			    "Bidirectional Forwarding Detection (BFD)
			     is enabled for this interface.";
		    }
		}
	    }

	    container routers {
		description
		    "Table of OSPF6 Router instances .";

		list router {
		    key vrf-id;

		    description
			"The router contains all information for one instance
			 of the OSPF6 protocol as supported by FRR.";

		    leaf vrf-id {
			type ospf6-vrf-id;
			description
			    "Each router is identified using the name of
			     a VRF, or the word 'default'.";
		    }

		    container areas {
			description
			    "The OSPF6 protocol operates on independent
			     link state regions called 'areas'.";

			list area {
			    key area-id;

			    leaf area-id {
				type ospf6-area-id;
				description
				    "Each area must have a unique ID
				     that takes the form of either a
				     dotted-quad or an unsigned 32-bit
				     number, interchangeably.  That
				     is, dotted-quad 0.0.0.1 is the
				     same as the unsigned number 1.";
			    }

			    container ranges {
				description
				    "Summarize intra-area paths from
				     speified area into one Type-3
				     Summary LSA announced to other areas.";

				list range {
				    key "prefix";

				    leaf prefix {
					type inet:ipv6-prefix;
					description
					    "Area range IPv6 prefix.";
				    }

				    container range-data {
					presence
					    "If present, hold range
					     data for the prefix.";

					leaf not-advertise {
					    type boolean;
					    description
						"If true, do not advertise
						 this prefix.";
					}

					leaf cost {
					    type uint32 {
						range "0..16777215";
					    }
					    description
						"Cost metric for this range.";
					}
				    }
				}
			    }

			    container stub {
				presence
				    "If present, configure area as a stub.";

				leaf no-summary {
				    type boolean;
				    description
					"Do not inject inter-area routes
					 into stub.";
				}
			    }
			}
		    }

		    container auto-cost {
			leaf reference-bandwidth {
			    type uint32 {
				range "1..4294967";
			    }
			    description
				"The reference bandwidth, 1..4294967,
				 in MBits/sec.";
			}
		    }

		    container distance {
			description
			    "OSPF6 administrative distances for routes.";

			leaf administrative {
			    type uint8 {
				range "1..255";
			    }
			    description
				"OSPF6 administrative distance.";
			}

			leaf external {
			    type uint8 {
				range "1..255";
			    }
			    description
				"OSPF6 administrative distance for external
				 routes.";
			}

			leaf inter-area {
			    type uint8 {
				range "1..255";
			    }
			    description
				"OSPF6 administrative distance for inter-area
				 routes.";
			}

			leaf intra-area {
			    type uint8 {
				range "1..255";
			    }
			    description
				"OSPF6 administrative distance for intra-area
				 routes.";
			}
		    }

		    container interfaces {
			description
			    "OSPF6 configuration informataion for
			     interfaces includes enablement,
			     cost and timing data.";

			list if {
			    key if-name;

			    leaf if-name {
				type string;
				description
				    "The interface with OSPF6 enabled
				    on it.";
			    }

			    leaf area-id {
				type inet:ipv4-address-no-zone;
				description
				    "The dotted-quad area identifier.";
			    }
			}
		    }

		    container log-adjacency-changes {
			presence
			    "If present, changes in adjacency state
			     will be logged.";

			leaf detail {
			    type boolean;
			    description
				"If true, all state changes will be logged.";
			}
		    }

		    container ospf6 {
			description
			    "OSPF6 attributes.";

			leaf router-id {
			    type yang:dotted-quad;
			    description
				"The unique ID of this OSPF6 router as a
				 dotted-quad.";
			}
		    }

		    container redistributions {
			description
			    "Configure which route types from other protocols
			     should be distributed into OSPF6.";

			list redistribution {
			    key source;

			    leaf source {
				type ospf6-redistribution;
				description
				    "The source of routes that will be
				     distributed into OSPF6.";
			    }

			    container redistribution-data {
				presence
				    "If present, routes from this source will
				     be distributed into OSPF6.";

				leaf route-map {
				    type string;
				    description
					"Route-map used to filter routes into
					 OSPF6.";
				}

			    }
			}
		    }

		    container stub-router {
			leaf administrative {
			    type boolean;
			    description
				"If true, this router will be a stub.";
			}
		    }

		    container timers {
			description
			    "OSPF6 timer configurations.";

			container lsa {
			    description
				"OSPF6 LSA timer configurations.";

			    leaf min-arrival {
				type uint32 {
				    range "0..600000";
				}
				description
				    "Mimimum delay in receiving new
				     versions of an LSA, in ms.";
			    }
			}

			container throttle {
			    description
				"Throttle adaptive timer configurations.";

			    container spf {
				description
				    "SPF timers.";

				leaf delay {
				    type uint32 {
					range "0..600000";
				    }
				    description
					"Delay from first received change until
					 SPF calculation, in ms.";
				}

				leaf initial-hold {
				    type uint32 {
					range "0..600000";
				    }
				    description
					"Initial hold time between consecutive
					 SPF calculation, in ms.";
				}

				leaf maximum-hold {
				    type uint32 {
					range "0..600000";
				    }
				    description
					"Maximum hold time, in ms.";
				}
			    }
			}
		    }
		}
	    }
	}
    }
}
