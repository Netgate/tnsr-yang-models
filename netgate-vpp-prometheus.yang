module netgate-vpp-prometheus {

    yang-version 1.1;

    namespace "urn:netgate:xml:yang:netgate-vpp-prometheus";
    prefix "ngvpppro";

    import netgate-cli-extensions {
        prefix "ngcliext";
    }

    import netgate-common {
        prefix "ngcom";
    }

    organization "Netgate";

    contact "Web: <http://www.netgate.com>";

    description
        "Provide RPCs to control VPP Prometheus Exporter
         Copyright 2018-2020 Rubicon Communications, LLC.
        ";

    revision 2021-02-15 {
	description
	    "TNSR Release 21.02.";
    }

    revision 2020-09-15 {
        description
            "Initial revision.";
    }


    rpc prometheus-control {
        input {
            leaf namespace {
                type ngcom:network-namespace;
		mandatory true;
                description
                    "operating namespace";
            }
            leaf operation {
                type ngcom:service-operation;
                mandatory true;
                description
                    "The operation to perform";
            }
        }
        output {
            leaf stdout {
                type string;
            }
        }
    }


    container prometheus-exporter {
	description
	    "configuration of the prometheus exporter";

	ngcliext:parent-fmt "prometheus";

	container host-space {
	    presence
	        "indicates the host namespace exporter
                 is enabled.";

	    ngcliext:node-fmt "$< host enable$n";
	    ngcliext:parent-fmt "$< host";

	    container filters {
	        description
		    "list of data items to export";
	    
		ngcliext:parent-fmt "$<";

	        leaf-list filter {
		    type string;
		    description
		        "regular expression for data to export";
		    ngcliext:node-fmt "$< $% @@$n";
	        }
	    }
	}

	container dataplane-space {
	    presence
	        "indicates the dataplane namespace exporter
                 is enabled.";

	    ngcliext:node-fmt "$< dataplane enable$n";
	    ngcliext:parent-fmt "$< dataplane";

	    container filters {
	        description
		    "list of data items to export";
	    
		ngcliext:parent-fmt "$<";

	        leaf-list filter {
		    type string;
		    description
		        "regular expression for data to export";
		    ngcliext:node-fmt "$< $% @@$n";
	        }
	    }
	}
    }
}
