module netgate-macip {

    yang-version 1.1;

    namespace "urn:netgate:xml:yang:netgate-macip";
    prefix "ngmacip";

    import ietf-inet-types {
	prefix "inet";
    }

    import ietf-yang-types {
	prefix "yang";
    }

    import netgate-cli-extensions {
	prefix "ngcliext";
    }

    import netgate-common {
	prefix "ngcom";
    }

    organization "Netgate";

    contact "Web: <http://www.netgate.com>";

    description
	"This YANG module provides a Netgate-defined data-model
	 for MACIP Access Control Lists.

	 Copyright 2019-2020 Rubicon Communications, LLC.
	 ";

    revision 2022-02-15 {
	description
	    "TNSR Release 22.02.";
    }

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-05-30 {
	description
	    "TNSR Release 19.05.";
    }

    revision 2019-04-30 {
	description
	  "Initial revision.";
    }

    typedef macip-rule-action {
	type enumeration {
	    enum deny {
		description
		    "Deny";
	    }
	    enum permit {
		description
		    "Permit";
	    }
	}
    }

    container "macip-config" {
	description
	    "MACIP ACL configuration in VPP.";

	container macip-table {
	    description
		"Table of MACIP lists, indexed by name.  Each entry
		 contains a set of MACIP Rules ordered by sequence number.";

	    list macip-list {
		key "macip-name";
		description
		    "MACIP list name.";

		ngcliext:node-fmt "macip @{macip-name}$n";
		ngcliext:pre-children-op "push";

		leaf macip-name {
		    type string;
		    mandatory true;
		    description
			"The MACIP name as supplied by the user.
			 It is a unique name used to identify this
			 set of MACIP Rules.";
		}

		leaf macip-description {
		    type ngcom:description-63;
		    description
		        "A text description for the MACIP.";
		    ngcliext:node-fmt "^description @@$n";
		}

		container macip-rules {
		    description
			"MACIP Rule Table ordered by sequence number.";

		    list macip-rule {
			key "sequence";
			description
			    "A List of MACIP Rules.";

			ngcliext:node-fmt "^rule @{sequence}$n";
			ngcliext:pre-children-op "push";

			leaf sequence {
			    type uint32;
			    description
				"Rules are executed in increasing sequence
				 number.";
			}

			leaf macip-rule-description {
			    type ngcom:description-63;
			    description
				"A text description for the MACIP.";
			    ngcliext:node-fmt "^description @@$n";
			}

			leaf action {
			    type macip-rule-action;
			    description
				"One of the actions 'deny' or 'permit'.";
			    ngcliext:node-fmt "^$% @@$n";
			}

			leaf mac-address {
			    type yang:mac-address;
			    description
			        "The L2 MAC address to be matched.";
			    ngcliext:node-fmt "^mac address @@$n";
			}

			leaf mac-mask {
			    type yang:mac-address;
			    description
			        "The L2 MAC mask ANDed with packet MAC
				addresses.";
			    ngcliext:node-fmt "^mac mask @@$n";
			}

			leaf ip-version {
			    type inet:ip-version;
			    mandatory true;
			    description
				"indicates the IP version (ipv4 or ipv6)
			         applicable to this ACL rule";
			    ngcliext:node-fmt "^$% @@$n";
			}

			leaf ip-prefix {
			    type inet:ip-prefix;
			    description
				"IP prefix.";
			    ngcliext:node-fmt "^address @@$n";
			}
		    }
		}
	    }
	}
    }

    container "macip-state" {
	config "false";

	description
	    "MACIP ACL state data.";

	container macip-table {
	    description
		"Table of MACIP lists, indexed by name.  Each entry
		 contains a set of MACIP Rules ordered by sequence number.";

	    list macip-list {
		key "macip-name";
		description
		    "MACIP list name.";

		leaf macip-name {
		    type string;
		    mandatory true;
		    description
			"The MACIP name as supplied by the developer.
			 It is a unique name used to identify this
			 set of MACIP Rules.";
		}

		container macip-rules {
		    description
			"MACIP Rule Table ordered by sequence number.";

		    list macip-rule {
			key "sequence";
			description
			    "A List of MACIP Rules.";

			leaf sequence {
			    type uint32;
			    description
				"Rules are executed in increasing sequence
				 number.";
			}

			leaf action {
			    type macip-rule-action;
			    description
				"One of the actions 'deny' or 'permit'.";
			}

			leaf mac-address {
			    type yang:mac-address;
			    description
			        "The L2 MAC address to be matched.";
			}

			leaf mac-mask {
			    type yang:mac-address;
			    description
			        "The L2 MAC mask ANDed with packet MAC
				addresses.";
			}

			leaf ip-version {
			    type inet:ip-version;
			    description
				"indicates the IP version (ipv4 or ipv6)
			         applicable to this MACIP rule";
			}

			leaf ip-prefix {
			    type inet:ip-prefix;
			    description
				"The IPv4 or IPv6 source prefix.";
			}
		    }
		}
	    }
	}
    }
}
