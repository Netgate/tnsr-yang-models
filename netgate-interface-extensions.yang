module netgate-interface-extensions {

    yang-version 1.1;

    namespace "urn:netgate:xml:yang:netgate-ifext";
    prefix "ngifext";

    import netgate-cli-extensions {
	prefix "ngcliext";
    }

    import netgate-interface {
	prefix "ngif";
    }

    import netgate-dataplane {
	prefix "ngdataplane";
    }

    organization "Netgate";

    contact "Web: <http://www.netgate.com>";

    description
	"This YANG module provides a data model for extended data for
	 a network interface.

	 Copyright 2019-2020 Rubicon Communications, LLC.";

    revision 2022-06-15 {
	description
	    "TNSR Release 22.06.";
    }

    revision 2021-02-15 {
	description
	    "TNSR Release 21.02.";
    }

    revision 2020-06-15 {
	description
	    "TNSR Release 20.06.";
    }

    revision 2020-02-15 {
	description
	    "TNSR Release 20.02.";
    }

    grouping interface-config-extensions {
	description
	    "The interface extensions configuration data contains interface
	     information that is not covered by standard data models.";

	list rx-queue {
	    key rx-queue-id;

	    ngcliext:parent-fmt "^$% @{rx-queue-id}";

	    leaf rx-queue-id {
		type uint16;
		description
		    "Queue number";
	    }

	    leaf pinned-cpu-id {
		type uint16;
		description
		    "CPU ID";
		must "/ngdataplane:dataplane-config/ngdataplane:cpu/ngdataplane:main-core = current() or
		      /ngdataplane:dataplane-config/ngdataplane:cpu/ngdataplane:corelist-workers/ngdataplane:corelist-worker[. = current()]" {
		    error-message "The pinned-cpu-id should be same as " +
				  "corelist-worker or main-core lcore id. ";
		}
		ngcliext:node-fmt "$< cpu @@$n";
	    }
	}
    }

    grouping interface-state-extensions {
	description
	    "The interface extensions state data contains interface
	     information that is not covered by standard data models.";
	
	list rx-queue {
	    key rx-queue-id;

	    leaf rx-queue-id {
		type uint16;
		description
		    "Queue number";
	    }

	    leaf pinned-cpu-id {
		type uint16;
		description
		    "CPU ID";
	    }

	    leaf rx-mode {
		type string;
		description
		    "Rx mode";
	    }
	}
    }

    augment "/ngif:interfaces-config/ngif:interface" {
	container rx-queues {

	must "not(/ngdataplane:dataplane-config/ngdataplane:cpu/ngdataplane:skip-cores)" {
	    error-message "Cannot configure rx-queue while using skip-cores.";
	}

	must "not(/ngdataplane:dataplane-config/ngdataplane:cpu/ngdataplane:workers)" {
	    error-message "Cannot configure rx-queue while using workers.";
	}

	    uses interface-config-extensions;
	}
    }

    augment "/ngif:interfaces-state/ngif:interface" {
	container rx-queues {
	    uses interface-state-extensions;
	}
    }

}
