module netgate-interface {

    yang-version 1.1;

    namespace "urn:netgate:xml:yang:netgate-interface";
    prefix "ngif";

    import clixon-lib {
	prefix "cl";
    }

    import ietf-inet-types {
	prefix "inet";
    }

    import ietf-yang-types {
	prefix "yang";
    }

    import netgate-cli-extensions {
	prefix "ngcliext";
    }

    import netgate-common {
	prefix "ngcom";
    }

    import netgate-macip {
	prefix "ngmacip";
    }

    import netgate-dataplane {
	prefix "ngdataplane";
    }

    organization "Netgate";

    contact "Web: <http://www.netgate.com>";

    description
	"This YANG module provides a data model for network interfaces.

	 Copyright 2017-2025 Rubicon Communications, LLC.
	";

    revision 2025-10-02 {
	description
	    "TNSR Release 25.10.";
    }

    revision 2025-06-02 {
	description
	    "TNSR Release 25.06.";
    }

    revision 2025-02-01 {
	description
	    "TNSR Release 25.02.";
    }

    revision 2024-10-01 {
	description
	    "TNSR Release 24.10.";
    }

    revision 2024-06-02 {
	description
	    "TNSR Release 24.06.";
    }

    revision 2023-11-01 {
	description
	    "TNSR Release 23.11.";
    }

    revision 2023-06-01 {
	description
	    "TNSR Release 23.06.";
    }

    revision 2023-02-01 {
	description
	    "TNSR Release 23.02.";
    }

    revision 2022-10-15 {
	description
	    "TNSR Release 22.10.";
    }

    revision 2022-06-15 {
	description
	    "TNSR Release 22.06.";
    }

    revision 2022-02-15 {
	description
	    "TNSR Release 22.02.";
    }

    revision 2021-11-15 {
	description
	    "TNSR Release 21.11.";
    }

    revision 2021-06-15 {
	description
	    "TNSR Release 21.07.";
    }

    revision 2021-02-15 {
	description
	    "TNSR Release 21.02.";
    }

    revision 2020-10-01 {
	description
	    "TNSR Release 20.10.";
    }

    revision 2020-07-15 {
	description
	    "TNSR Release 20.07.";
    }

    revision 2020-06-15 {
	description
	    "TNSR Release 20.06.";
    }

    revision 2020-04-16 {
	description
	    "Reorganized ACLs applied to an interface in state data.
	     Added sequence number, and used this for key";
    }

    revision 2020-02-26 {
	description
	    "Added IPv4 MTU and IPv6 MTU data nodes.";
    }

    revision 2020-02-15 {
	description
	    "TNSR Release 20.02.";
    }

    revision 2019-12-15 {
	description
	    "TNSR Release 19.12.";
    }

    revision 2019-08-30 {
	description
	    "TNSR Release 19.08.";
    }

    revision 2019-05-30 {
	description
	    "TNSR Release 19.05.";
    }

    revision 2017-01-06 {
	description
	    "Initial revision.";
    }


    typedef interface-ref {
	type leafref {
	    path "/ngif:interfaces-config/ngif:interface/ngif:name";
	}
	description
	    "This type is used by data models that need to reference
	     interfaces.";
    }

    typedef loopback-name-63 {
	type string {
	    pattern '[a-zA-Z_0-9][a-zA-Z0-9_/.-]*';
	    length "1..63";
	}
    }

    typedef intf-vlan-id {
	type union {
	    type uint16 {
		range "1..4095";
	    }
	    type string {
		pattern "any";
	    }
	}
    }

    typedef intf-tag-rewrite-op {
	type enumeration {
	    enum disable {
		description
		    "IPv4";
	    }
	    enum pop-1 {
		description
		    "Pop 1";
	    }
	    enum pop-2 {
		description
		    "Pop 2";
	    }
	    enum push-1 {
		description
		    "Push 1";
	    }
	    enum push-2 {
		description
		    "Push 2";
	    }
	    enum translate-1-1 {
		description
		    "Translate 1 1";
	    }
	    enum translate-1-2 {
		description
		    "Translate 1 2";
	    }
	    enum translate-2-1 {
		description
		    "Translate 2 1";
	    }
	    enum translate-2-2 {
		description
		    "Translate 2 2";
	    }
	}
    }

    typedef bond-mode {
	type enumeration {
	    enum round-robin {
		value 1;
		description
		    "Round robin";
	    }
	    enum active-backup {
		value 2;
		description
		    "Active backup";
	    }
	    enum xor {
		value 3;
		description
		    "XOR";
	    }
	    enum broadcast {
		value 4;
		description
		    "Broadcast";
	    }
	    enum lacp {
		value 5;
		description
		    "LACP";
	    }
	}
    }

    typedef bond-xor-lacp-load-balance {
	type enumeration {
	    enum l2 {
		value 0;
		description
		    "L2";
	    }
	    enum l34 {
		value 1;
		description
		    "L34";
	    }
	    enum l23 {
		value 2;
		description
		    "L23";
	    }
	}
    }

    typedef intf-rx-mode {
	type enumeration {
	    enum polling {
		description
		    "polling";
	    }
	    enum interrupt {
		description
		    "interrupt";
	    }
	    enum adaptive {
		description
		    "adaptive";
	    }
	}
    }

    typedef bond-load-balance {
	type enumeration {
	    enum l2 {
		value 0;
		description
		    "L2";
	    }
	    enum l34 {
		value 1;
		description
		    "L34";
	    }
	    enum l23 {
		value 2;
		description
		    "L23";
	    }
	    enum round-robin {
		value 3;
		description
		    "round-robin";
	    }
	    enum broadcast {
		value 4;
		description
		    "broadcast";
	    }
	    enum active-backup {
		value 5;
		description
		    "active-backup";
	    }
	}
    }

    typedef lacp-rx-state {
	type enumeration {
	    enum INITIALIZE {
		value 0;
		description
		    "Initialize";
	    }
	    enum PORT_DISABLED {
		value 1;
		description
		    "Port disabled";
	    }
	    enum EXPIRED {
		value 2;
		description
		    "Expired";
	    }
	    enum LACP_DISABLED {
		value 3;
		description
		    "LACP disabled";
	    }
	    enum DEFAULTED {
		value 4;
		description
		    "Defaulted";
	    }
	    enum CURRENT {
		value 5;
		description
		    "Current";
	    }
	}
    }

    typedef lacp-tx-state {
	type enumeration {
	    enum TRANSMIT {
		value 0;
		description
		    "Transmit PDU";
	    }
	}
    }

    typedef lacp-mux-state {
	type enumeration {
	    enum DETACHED {
		value 0;
		description
		    "Detached";
	    }
	    enum WAITING {
		value 1;
		description
		    "Waiting";
	    }
	    enum ATTACHED {
		value 2;
		description
		    "Attached";
	    }
	    enum COLLECTING_DISTRIBUTING {
		value 3;
		description
		    "Collecting distributing";
	    }
	}
    }

    typedef lacp-ptx-state {
	type enumeration {
	    enum NO_PERIODIC {
		value 0;
		description
		    "No periodic";
	    }
	    enum FAST_PERIODIC {
		value 1;
		description
		    "Fast periodic";
	    }
	    enum SLOW_PERIODIC {
		value 2;
		description
		    "Slow periodic";
	    }
	    enum PERIODIC_TX {
		value 3;
		description
		    "Periodic transmission";
	    }
	}
    }

    typedef ip-reassembly-type {
	type enumeration {
	    enum full {
		value 0;
		description
		    "Full ip-reassembly";
	    }
	    enum virtual {
		value 1;
		description
		    "Shallow virtual ip-reassembly";
	    }
	}
    }

    typedef mss-clamp-direction {
	type enumeration {
	    enum Tx {
		description
		    "The MSS clamp value applies to transmitted packets.";
	    }
	    enum Rx {
		description
		    "The MSS clamp value applies to received packets.";
	    }
	    enum TxRx {
		description
		    "The MSS clamp value applies to both transmitted and
		     received packets.";
	    }
	}
    }

    typedef memif-mode {
	type enumeration {
	    enum ethernet {
		description
		    "Ethernet mode";
	    }
	    enum ip {
		description
		    "IP mode";
	    }
	}
    }

    rpc clear-interface-counters {
	input {
	    leaf interface {
		type string;
		description
		    "Should be a valid interface name.	No name implies
		     clear all interfaces.";
	    }
	}
    }

    rpc packet-counters {
	output {
	    leaf stdout {
		type string;
	    }
	}
    }

    container interfaces-config {
	description
	    "Interface configuration parameters.";

	ngcliext:children-top-sort "interface-ts"; 

	list interface {
	    key "name";

	    ngcliext:context "intf-interfaces,intf-vrrp";

	    description
		"The list of configured interfaces on the device.";

	    ngcliext:pre-children-op  "push";
	    ngcliext:node-fmt "interface @{name}$n";

	    leaf name {
		type string;
		description
		    "The name of the interface.";
	    }

	    leaf description {
		type ngcom:description-63;
		description
		    "A textual description of the interface.";
		ngcliext:context "intf-interfaces";
		ngcliext:node-fmt "^$% @@$n";
		cl:ignore-compare;
	    }

	    leaf enabled {
		type boolean;
		description
		    "This leaf contains the configured, desired state of
		     the interface.";
		ngcliext:context "intf-interfaces";
		ngcliext:node-fmt "^disable$n|^enable$n";
		ngcliext:node-op  "bool";
	    }

	    leaf mtu {
		type uint16 {
		    range "0 | 68..max";
		}
		units octets;
		/*
		 * With no-multi-seg, a received frame must fit into a single
		 * buffer: the MTU plus 22 (the Ethernet header and two VLAN
		 * tags) must not exceed the buffer data size, which is 2048
		 * when not configured. VPP refuses larger MTUs. The ethernet
		 * default-mtu is checked in netgate-dataplane.
		 */
		must "not(/ngdataplane:dataplane-config/ngdataplane:dpdk/"
		   + "ngdataplane:no-multi-seg = 'true') or "
		   + "(not(/ngdataplane:dataplane-config/ngdataplane:buffers/"
		   + "ngdataplane:default-data-size) and current() <= 2026) or "
		   + "current() <= /ngdataplane:dataplane-config/"
		   + "ngdataplane:buffers/ngdataplane:default-data-size - 22" {
		    error-message
			"With dataplane dpdk no-multi-seg, the MTU must not "
		      + "exceed the dataplane buffers default-data-size minus "
		      + "22 (2026 when default-data-size is not configured)";
		}
		description
		    "The size, in octets, of the largest packet that the
		     interface will send and receive.";
		ngcliext:context "intf-interfaces";
		ngcliext:node-fmt "^$% @@$n";
	    }

	    leaf mac-address {
		type yang:mac-address;
		description
		    "The Media Access Control (MAC) address of the
		    interface.";
		ngcliext:context "intf-interfaces";
		ngcliext:node-fmt "^$% @@$n";
	    }

	    leaf host-tap-name {
		type string;
		description
		    "If this interface is associated with a host tap,
		     this field names that host tap interface.";
	    }

	    leaf rx-mode {
		type ngif:intf-rx-mode;
		must 'not(starts-with(../name, "BondEthernet"))' {
		    error-message
			"Cannot set rx-mode for a bond interface.";
		}
		must 'not(starts-with(../name, "loop"))' {
		    error-message
			"Cannot set rx-mode for a loopback interface.";
		}
		description
		    "Rx mode";
		ngcliext:context "intf-interfaces";
		ngcliext:node-fmt "^$% @@$n";
	    }

	    leaf vrf {
		type ngcom:rt-identifier-15;
		description
		    "The name of the VRF this interface is bound to.";
		ngcliext:context "intf-interfaces";
		ngcliext:node-fmt "^$% @@$n";
	    }

	    container ipv4 {
		presence
		    "Enables IPv4";
		description
		    "Parameters for the IPv4 address family.";

		ngcliext:parent-fmt "^ip";
		
		container address {
		    ngcliext:context "intf-interfaces";
		    ngcliext:parent-fmt "$< address";

		    leaf-list ip {
			type inet:ipv4-prefix;
			description
			    "An IPv4 address on the interface.";
			ngcliext:node-fmt "$< @@$n";
		    }
		}

		container reassembly {
		    description
			"ip-reassembly feature control.";
		    ngcliext:context "intf-interfaces";
		    ngcliext:parent-fmt "$< reassembly";

		    presence
			"make container work the way code expects";
		    
		    leaf enabled {
			type boolean;
			description
			    "IPv4 reassembly enabled for interface";
			ngcliext:node-op "bool";
			ngcliext:node-fmt "|$< enable$n";
		    }

		    leaf reassembly-type {
			type ip-reassembly-type;
			default full;
			description
			    "Type of ip-reassembly on interface";
			ngcliext:node-fmt "$< type @@$n";
		    }
		}

		leaf mtu {
		    type uint16 {
			range "0 | 68..max";
		    }
		    units "octets";
		    description
			"The size, in octets, of the largest IPv4 packet that
			 the interface will send and receive.";
		    ngcliext:context "intf-interfaces";
		    ngcliext:node-fmt "$< $% @@$n";
		}

		container tcp {
		    description
			"IPv4 TCP configuration values.";
		    ngcliext:context "intf-interfaces";
		    ngcliext:parent-fmt "$< tcp";

		    container mss {
			description
			    "IPv4 TCP Maximum Segment Size values.";
			ngcliext:node-fmt "$< $% @{value} @{directions}$n";

			leaf value {
			    type uint16;
			    units "octets";
			    must '../directions != ""' {
				error-message
				    "Both 'directions' and 'value' must
				     be set.";
			    }
			    description
				"The IPv4 TCP maximum segment size.";
			}

			leaf directions {
			    type mss-clamp-direction;
			    must '../value != ""' {
				error-message
				    "Both 'direction' and 'value' must
				     be set.";
			    }
			    description
				"The directions to which the MSS applies.";
			}
		    }
		}

		leaf unnumbered {
		    type ngcom:if-identifier-63 {
			path "/ngif:interfaces-config"
			    + "/ngif:interface"
			    + "/ngif:name";
		    }
		    must 'not(../address)' {
			error-message "Unnumbered interfaces cannot have an address.";
		    }
		    must 'current() != ../../name' {
			error-message "Unnumbered interfaces cannot refer to itself.";
		    }
		    description
			    "This interface this interfaces is associated with.";
		    ngcliext:context "intf-interfaces";
		    ngcliext:node-fmt "$< $% @@$n";
		}
	    }

	    container ipv6 {
		presence
		    "Enables IPv6";
		description
		    "Parameters for the IPv6 address family.";
		must './ngif:mtu or ../ngif:mtu >= 1280 or /ngdataplane:dataplane-config/ngdataplane:ethernet/ngdataplane:default-mtu >= 1280' {
		    error-message
			"IPv6 mandates an MTU 1280 or greater";
		}
		ngcliext:parent-fmt "^ipv6";
		
		container address {
		    ngcliext:context "intf-interfaces";
		    ngcliext:parent-fmt "$< address";

		    leaf-list ip {
			type inet:ipv6-prefix;
			description
			    "An IPv6 address on the interface.";
			ngcliext:node-fmt "$< @@$n";
		    }
		}

		container reassembly {
		    description
			"ip-reassembly feature control.";
		    ngcliext:context "intf-interfaces";
		    ngcliext:parent-fmt "$< reassembly";

		    presence
			"make container work the way the code expects";
		    
		    leaf enabled {
			type boolean;
			description
			    "IPv6 reassembly enabled for interface";
			ngcliext:node-op "bool";
			ngcliext:node-fmt "|$< enable$n";
		    }
		    leaf reassembly-type {
			type ip-reassembly-type;
			default full;
			description
			    "Type of ip-reassembly on interface";
			ngcliext:node-fmt "$< type @@$n";
		    }
		}

		leaf mtu {
		    type uint32 {
			range "1280..max";
		    }
		    units "octets";
		    description
			"The size, in octets, of the largest IPv6 packet that
			 the interface will send and receive.";
		    ngcliext:context "intf-interfaces";
		    ngcliext:node-fmt "$< $% @@$n";
		}

		container tcp {
		    description
			"IPv6 TCP configuration values.";
		    ngcliext:context "intf-interfaces";
		    ngcliext:parent-fmt "$< tcp";

		    container mss {
			description
			    "IPv6 TCP Maximum Segment Size values.";
			ngcliext:node-fmt "$< $% @{value} @{directions}$n";

			leaf value {
			    type uint16;
			    units "octets";
			    must '../directions != ""' {
				error-message
				    "Both 'directions' and 'value' must
				     be set.";
			    }
			    description
				"The IPv4 TCP maximum segment size.";
			}

			leaf directions {
			    type mss-clamp-direction;
			    must '../value != ""' {
				error-message
				    "Both 'direction' and 'value' must
				     be set.";
			    }
			    description
				"The directions to which the MSS applies.";
			}
		    }
		}
	    }

	    container bridge {
		presence
		    "indicates this interface is part of a bridge";

		description
		    "If the interface is being used as a bridge, this
		     node contains the corresponding Bridge Domain Id,
		     Split Horizon, and/or Bridge Virtual Id information.";

		ngcliext:context "intf-interfaces";

		leaf bdi {
		    type uint32;
		    description
			"Bridge Domain Id.";
		    ngcliext:node-fmt "^bridge domain @@%{bvi}%{shg}$n";
		}

		leaf bvi {
		    type boolean;
		    description
			"Set up the interface as a BVI.";
		    ngcliext:sibling-op "bool";
		    ngcliext:sibling-fmt "| $%";
		}

		leaf shg {
		    type uint8;
		    description
			"Split Horizon Group.";
		    ngcliext:sibling-fmt " $% @@";
		}
	    }

	    container dhcp-client {
		presence
		    "indicates that this interface has a DHCP client";

		description
		    "If the interface is configured using a DHCP client,
		     that configuration is contained here.";

		ngcliext:context "intf-interfaces";
		ngcliext:node-fmt "^dhcp client ipv4";
		ngcliext:post-node-fmt "$n";

		must "not(../ipv4/ngif:unnumbered)" {
		    error-message
		        "DHCP client cannot be on an unnumbered interface";
		}

		leaf enable {
		    type boolean;
		    default false;
		}

		leaf hostname {
		    type string {
			/*
			 * RFC-1123, RFC-2181.
			 */
			 pattern '[a-zA-Z0-9]([-a-zA-Z0-9]){0,62}';
		    }
		    description
			"An optional hostname to use.";
		    ngcliext:node-fmt " $% @@";
		}
	    }

	    container access-list {
		presence
		    "Indicates that this interface has ACLs";

		description
		    "If the interface has any Access Control Lists,
		     they are listed here in two groups: those that apply
		     to packet ingress and those that apply to egresss.
		     The two sets of ACLs are sorted independenty and
		     applied in ascending sequence-number order.";

		ngcliext:context "intf-interfaces";

		container input {
		    description
			"These are the ACL rule-sets that apply to ingress
			packets.";

		    list acl-list {
			key "acl-name";
			description
			    "Each ACL rule-set can appear at most once within
			     the input list.";

			ngcliext:node-fmt "^access-list input acl @{acl-name} sequence @{sequence}$n";

			leaf acl-name {
			    type string;
			    description
				"This is the name of an ACL rule-set
				 that will be be applied to packets on
				 this interface.";
			}

			leaf sequence {
			    type uint32;
			    description
				"Set the ordering of the ACLs. Rules are
				 applied in ascending sequence number.";
			}
		    }
		}

		container output {
		    description
			"These are the ACL rule-sets that apply to egress
			 packets.";

		    list acl-list {
			key "acl-name";
			description
			    "Each ACL rule-set can appear at most once within
			     the output list.";

			ngcliext:node-fmt "^access-list output acl @{acl-name} sequence @{sequence}$n";

			leaf acl-name {
			    type string;
			    description
				"This is the name of an ACL rule-set
				 that will be be applied to packets on
				 this interface.";
			}

			leaf sequence {
			    type uint32;
			    description
				"Set the ordering of the ACLs. Rules are
				 applied in ascending sequence number.";
			}
		    }
		}

		container macip {
		    description
			"An interface may also have at most one ACL
			 based upon a combination of MAC address and
			 IP.  If that ACL is present, it is always on
			 the ingress packets.";

		    ngcliext:node-fmt "^access-list macip @{macip-name}$n";

		    leaf macip-name {
			type leafref {
			    path "/ngmacip:macip-config"
			        + "/ngmacip:macip-table"
			        + "/ngmacip:macip-list"
				+ "/ngmacip:macip-name";
			}
			description
			    "This name references at most one MACIP ingress
			     rule-set from the ACL MACIP tables.";
		    }
		}
	    }

	    leaf collect-detailed-stats {
		type boolean;
		description
		    "enable detailed counter keeping in VPP";
		ngcliext:context "intf-interfaces";
		ngcliext:node-op "bool";
		ngcliext:node-fmt "|^detailed-stats enable$n";
	    }

	    container lldp {
		presence
		    "Indicates this interface has LLDP configured";

		ngcliext:context "intf-interfaces";
		ngcliext:node-op "test-set:@{port-name}@{management}";
		ngcliext:node-fmt "^lldp$n|";

		leaf port-name {
		    type string;
		    description
			"Port name used in LLDP packet.";
		    ngcliext:node-fmt "^lldp port-name @@$n";
		}

		container management {
		    leaf ipv4-address {
			type inet:ipv4-address-no-zone;
			description
			    "IPv4 management address.";
			ngcliext:node-fmt "^lldp management ipv4 @@$n";
		    }

		    leaf ipv6-address {
			type inet:ipv6-address-no-zone;
			description
			    "IPv6 management address.";
			ngcliext:node-fmt "^lldp management ipv6 @@$n";
		    }

		    leaf oid {
			type ngcom:object-id-128;
			description
			    "Management object ID.";
			ngcliext:node-fmt "^lldp management oid @@$n";
		    }
		 }
	    }

	    container bond {
		presence
		    "indicates this interface is a slave of a bonded interface";

		description
		    "If the interface is being used as a slave, this node
		     contains the corresponding bond ID and slave options.";

		ngcliext:context "intf-interfaces";

		must "not(../ipv4)" {
		    error-message "IPv4 config not allowed on bond slave interfaces.";
		}
		must "not(../ipv6)" {
		    error-message "IPv6 config not allowed on bond slave interfaces.";
		}
		must "not(../mac-address or ../vrf or ../bridge or ../dhcp-client or ../access-list or ../lldp or ../map or ../vlan-tag-rewrite)" {
		    error-message "Invalid configuration on bond slave interface.";
		}

		leaf instance {
		    type uint32;
		    description
			"Bond unique identifier.";
		    ngcliext:node-fmt "^bond @@%{long-timeout}%{passive}$n";
		}

		leaf passive {
		    type boolean;
		    default false;
		    description
			"The slave interface does not
			 initiate the LACP protocol,
			 remote must be active speaker.";
		    ngcliext:sibling-op "bool";
		    ngcliext:sibling-fmt "| $%";
		}

		leaf long-timeout {
		    type boolean;
		    default false;
		    description
			"90 seconds VS default 3 seconds
			 neighbor timeout.";
		    ngcliext:sibling-op "bool";
		    ngcliext:sibling-fmt "| $%";
		}
	    }

	    container map {
		presence
		    "this interface perform MAP translations";

		description
		    "Per-interface parameters for MAP-E and MAP-T.";

		ngcliext:context "intf-interfaces";

		leaf enabled {
		    type boolean;
		    description
			"If true, MAP-E encapsulation or MAP-T
			 translations are enabled on this interface.";
		    ngcliext:node-op "bool";
		    ngcliext:node-fmt "|^map enable$n";
		}

		leaf is-translation {
		    type boolean;
		    description
			"If true, this interface is performing MAP-T
			 translations.	If false, this interface is
			 performing encapsuations.  Valid only when
			 also enabled.";
		    ngcliext:node-op "bool";
		    ngcliext:node-fmt "|^map translate$n";
		}
	    }

	    container vlan-tag-rewrite {
		presence
		    "this interface rewrite VLAN tags";

		ngcliext:context "intf-interfaces";

		leaf operation {
		    type intf-tag-rewrite-op;
		    description
			"A tag rewrite operation is one of the strings:
			 'disable', 'pop-1', 'pop-2', 'push-1', 'push-2',
			 'translate-1-1', 'translate-1-2',
			 'translate-2-1', 'translate-2-2'.";
		    ngcliext:node-fmt "^vlan tag-rewrite @@%{push-dot1q}%{tag1}%{tag2}$n";
		}

		leaf push-dot1q {
		    type boolean;
		    default false;
		    description
			"If true the first pushed tag is of type dot1q,
			 otherwise it will be of type dot1ad.";
		    ngcliext:sibling-op "bool";
		    ngcliext:sibling-fmt " dot1ad| dot1q";
		}

		leaf tag1 {
		    type uint32;
		    description
			"The first pushed tag value.";
		    ngcliext:sibling-fmt " @@";
		}

		leaf tag2 {
		    type uint32;
		    description
			"The second pushed tag value.";
		    ngcliext:sibling-fmt " @@";
		}
	    }
	}

	container bridge-table {
	    description
		"Bridge mapping table.";

	    ngcliext:context "intf-bridge";

	    list bridge-entry {
		key "bdi";
		description
		    "Bridge Domain Id.";

		ngcliext:node-fmt "interface bridge domain @{bdi}$n";
		ngcliext:pre-children-op  "push";

		leaf bdi {
		    type uint32 {
			range "1..16777215";
		    }
		    mandatory true;
		    description
			"The Bridge Domain Identifier.	A unique number
			 for this entry.";
		}

		leaf description {
		    type ngcom:description-63;
		    description
			"A textual description of the bridge.";
		    ngcliext:node-fmt "^$% @@$n";
		    cl:ignore-compare;
		}

		leaf flood {
		    type boolean;
		    description
			"Broadcast/multicast flooding in the bd";
		    ngcliext:node-op  "bool";
		    ngcliext:node-fmt "^no $%$n|^$%$n";
		}

		leaf uu-flood {
		    type boolean;
		    description
			"Unknown unicast flood in the bd";
		    ngcliext:node-op  "bool";
		    ngcliext:node-fmt "|^$%$n";
		}

		leaf forward {
		    type boolean;
		    description
			"Forwarding on all interfaces in the bd";
		    ngcliext:node-op  "bool";
		    ngcliext:node-fmt "|^$%$n";
		}

		leaf learn {
		    type boolean;
		    description
			"Learning on all interfaces in the bd";
		    ngcliext:node-op  "bool";
		    ngcliext:node-fmt "|^$%$n";
		}

		leaf arp-term {
		    type boolean;
		    description
			"ARP termination in the bd";
		    ngcliext:node-op  "bool";
		    ngcliext:node-fmt "|^arp term$n";
		}

		leaf mac-age {
		    type uint8;
		    description
			"MAC aging time in min, 0 for disabled.";
		    ngcliext:node-fmt "$% @@$n";
		}

		container bridge-arp-table {
		    description
			"Bridge ARP Entry Table.";

		    list bridge-arp-entry {
			key "ip-address";
			description
			    "Bridge ARP entry table.";

			ngcliext:node-fmt "^arp entry ip @{ip-address} mac-address @{mac-address}$n";

			leaf ip-address {
			    type inet:ip-address-no-zone;
			    description
				"The IPv4 or IPv6 address of an ARP entry.";
			}

			leaf mac-address {
			    type yang:mac-address;
			    description
				"The MAC address of an ARP entry.";
			}
		    }
		}
	    }
	}

	container loopback-table {
	    description
		"Loopback name table.";

	    ngcliext:context "intf-loopback";

	    list loopback {
		key "name";
		unique "instance";
		description
		    "Loopback name.";

		ngcliext:node-fmt "interface loopback @{name}$n";
		ngcliext:pre-children-op  "push";

		leaf name {
		    type loopback-name-63;
		    description
			"The identifier.  A unique name
			 for this Loopback entry.";
		}

		leaf instance {
		    type uint16;
		    mandatory true;
		    description
			"Each Loopback creates an interface.  The
			 interface will be named 'loopback<X>',
			 where the <X> is the instance number.
			 The instance number must be unique
			 across all Loopback interfaces.";
		    ngcliext:node-fmt "^$% @@$n";
		}

		leaf mac-address {
		    type yang:mac-address;
		    description
			"The MAC address for the interface.";
		    ngcliext:node-fmt "^$% @@$n";
		}

		leaf description {
		    type ngcom:description-63;
		    description
			"A user description of the Loopback.";
		    ngcliext:node-fmt "^$% @@$n";
		    cl:ignore-compare;
		}
	    }
	}

	container socket-table {
	    description
		"Host memif socket table.";

	    ngcliext:context "intf-memif-socket";

	    list socket {
		key "id";
		description
		    "A unique 32-bit integer identifying this socket
		     filename.";

		ngcliext:node-fmt "interface memif socket @{id} filename @{filename}$n";

		leaf id {
		    type uint32 {
			range "1..max";
		    }
		    description
			"This is the user assigned id of the socket
			 filename.";
		}

		leaf filename {
		    type string;
		    mandatory true;
		    description
			"The path to a socket file used for establishing
			 memif connections.  A socket can be used for
			 either server or client interfaces, but not both.
			 A socket can have more than one server using it,
			 or it can have more than one client using it.";
		}
	    }
	}

	container memif-table {
	    description
		"Host memif interface configuration table.";

	    ngcliext:context "intf-memif-table";

	    list memif-entry {
		key "socket-id memif-id";
		description
		    "A unique 32-bit integer identifying this interface.";

		ngcliext:node-fmt "interface memif socket @{socket-id} interface @{memif-id}$n";
		ngcliext:pre-children-op  "push";

		leaf socket-id {
		    type uint32;
		    description
			"The socket-id of the socket filename to use
			 in establishing a connection.";
		}

		leaf memif-id {
		    type uint32;
		    description
			"This is the user assigned id of the memif interface.";
		}

		leaf buffer-size {
		    type uint32;
		    description
			"The size of the buffer allocated for each
			 ring entry.  Default 2048.";
		    ngcliext:node-fmt "^$% @@$n";
		}

		leaf mac-address {
		    type yang:mac-address;
		    description
			"The MAC address for the interface.";
		    ngcliext:node-fmt "^$% @@$n";
		}

		leaf mode {
		    type memif-mode;
		    mandatory true;
		    description
			"Should be 'ethernet', 'IP' or 'punt/inject'.";
		    ngcliext:node-fmt "^$% @@$n";
		}

		leaf ring-size {
		    type uint8 {
			range "8..32";
		    }
		    description
			"The number of entries in the rx/tx rings.
			 The number of entries must be a power of 2
			 This number is that power of 2, between 8 and 32.
			 The default is 10, for 1024 entries.";
		    ngcliext:node-fmt "^$% @@$n";
		}

		leaf secret {
		    type string {
			length "1..24";
		    }
		    description
			"The secret is used to match and authenticate
			 the other end of the connection.";
		    ngcliext:node-fmt "^$% $q@@$q$n";
		}

		choice role {
		    mandatory true;
		    description
			"Interface role (client or server).";
		    case client {
			container client {
			    presence
				"If present, the role of this memif is 'client'.";

			    ngcliext:node-fmt "^role client$n";
			    ngcliext:parent-fmt "^role client";

			    leaf rx-queues {
				type uint8 {
				    range "1..255";
				}
				description
				    "The number of slave rx queues.";
				ngcliext:node-fmt "$< $% @@$n";
			    }

			    leaf tx-queues {
				type uint8 {
				    range "1..255";
				}
				description
				    "The number of slave tx queues.";
				ngcliext:node-fmt "$< $% @@$n";
			    }
			}
		    }
		    case server {
			container server {
			    presence
				"If present, the role of this memif is 'server'.";

			    ngcliext:node-fmt "^role server$n";
			}
		    }
		}
	    }
	}

	container subinterfaces {
	    description
		"An interface may have subinterfaces.";

	    ngcliext:context "intf-subif";

	    list subif-entry {
		key "if-name subid";
		description
		    "Each subinterface entry represents a VLAN.";

		ngcliext:node-fmt "interface subif @{if-name} @{subid}$n";
		ngcliext:pre-children-op "push";

		leaf if-name {
		    type string;
		    description
			"The interface on which this subinterface exists.";
		}

		leaf subid {
		    type uint32 {
			range "0..4294967294";
		    }
		    description
			"The subinterface id.  It is often also the (outer)
			 VLAN tag value, though they can be different.";
		}

		container vlan {
		    description
			"These fields all contribute to the subinterface
			 definition for VLAN handling.";

		    leaf dot1ad {
			type boolean;
			description
			    "By default the outer tag is dot1q.	 If this
			     value is true, it is instead dot1ad.";
			ngcliext:sibling-op "bool";
			ngcliext:sibling-fmt "|true";
		    }

		    leaf exact-match {
			type boolean;
			description
			    "By default matching is non-exact.	If this
			     value is true, matching is exact.";
			ngcliext:node-op "bool";
			ngcliext:node-fmt "|^$%$n";
		    }

		    leaf default-subif {
			type boolean;
			description
			    "The default subinterface is associated with a
			     packet that did not match any other configured
			     subinterface on this interface.";
			ngcliext:node-op "bool";
			ngcliext:node-fmt "|^$%$n";
		    }

		    leaf outer-vlan-id {
	    		type uint16 {
			    range "1..4095";
	    		}
			description
			    "The outer vlan tag id.  It can be an integer
			     between 1 and 4095 inclusive.";
			ngcliext:node-op "test-set:%{dot1ad}";
			ngcliext:node-fmt "^outer-dot1q @@$n|^outer-dot1ad @@$n";
		    }

		    leaf inner-vlan-id {
			type intf-vlan-id;
			description
			    "The inner vlan tag id.  It can be an integer
			     between 1 and 4095 inclusive, or the word 'any'.";
			ngcliext:node-fmt "^inner-dot1q @@$n";
		    }
		}
	    }
	}

	container tap-table {
	    description
		"Host Tap interface configuration table.";

	    ngcliext:context "intf-tap";

	    list tap {
		key "host-name";
		unique "instance";

		description
		    "Unique identifing host tap name.";

		ngcliext:node-fmt "^interface tap @{host-name}$n";
		ngcliext:pre-children-op "push";

		leaf host-name {
		    type string;
		    description
			"The name of the tap on the host system.";
		}

		leaf host-bridge {
		    type string;
		    description
			"The host bridge to which the tap will be attached.";
		    ngcliext:node-fmt "^host bridge @@$n";
		}

		leaf host-ipv4-gateway {
		    type inet:ipv4-address-no-zone;
		    description
			"The IPv4 gateway address on the interface.";
		    ngcliext:node-fmt "^host ipv4 gateway @@$n";
		}

		leaf host-ipv4-prefix {
		    type inet:ipv4-prefix;
		    description
			"The IPv4 prefix on the interface.";
		    ngcliext:node-fmt "^host ipv4 prefix @@$n";
		}

		leaf host-ipv6-gateway {
		    type inet:ipv6-address-no-zone;
		    description
			"The IPv6 gateway address on the interface.";
		    ngcliext:node-fmt "^host ipv6 gateway @@$n";
		}

		leaf host-ipv6-prefix {
		    type inet:ipv6-prefix;
		    description
			"The IPv6 prefix on the interface.";
		    ngcliext:node-fmt "^host ipv6 prefix @@$n";
		}

		leaf host-mac-address {
		    type yang:mac-address;
		    description
			"The MAC address of the host tap interface.";
		    ngcliext:node-fmt "^host mac-address @@$n";
		}

		leaf host-namespace {
		    type ngcom:network-namespace;
		    default dataplane;
		    description
			"The host namespace in which the tap will be made.";
		    ngcliext:node-fmt "^host namespace @@$n";
		}

		leaf instance {
		    type uint32 {
			range "0..4095";
		    }
		    mandatory true;
		    description
			"The tap instance number.";
		    ngcliext:node-fmt "^$% @@$n";
		}

		leaf mac-address {
		    type yang:mac-address;
		    description
			"The MAC address of the interface.";
		    ngcliext:node-fmt "^$% @@$n";
		}

		leaf rx-ring-size {
		    type uint8 {
			range "0..15";
		    }
		    description
			"A power of 2 between 0 and 15 inclusive yielding
			 a receive ring size 32 to 32768 entries.  The
			 default is 8 (256 entries).";
		    ngcliext:node-fmt "^$% @@$n";
		}

		leaf tx-ring-size {
		    type uint8 {
			range "0..15";
		    }
		    description
			"A power of 2 between 0 and 15 inclusive yielding
			 a transmit ring size 32 to 32768 entries.  The
			 default is 8 (256 entries).";
		    ngcliext:node-fmt "^$% @@$n";
		}
	    }
	}

	container bond-table {
	    description
		"Bond interface configuration table.";

	    ngcliext:context "intf-bond";

	    list bond {
		key "instance";
		description
		    "Bond interface.";

		ngcliext:node-fmt "^interface bond @{instance}$n";
		ngcliext:pre-children-op "push";

		leaf instance {
		    type uint32;
		    description
			"The identifier. A unique number
			 for this bond interface.";
		}

		leaf mode {
		    type bond-mode;
		    mandatory true;
		    description
			"The mode for the interface.";
		    ngcliext:node-fmt "^$% @@$n";
		}

		leaf mac-address {
		    type yang:mac-address;
		    description
			"The MAC address for the interface.";
		    ngcliext:node-fmt "^$% @@$n";
		}

		leaf load-balance {
		    type bond-xor-lacp-load-balance;
		    default l2;
		    description
			"The load balance for the interface
			 (valid for XOR and LACP modes).";
		    ngcliext:node-fmt "^$% @@$n";
		}
	    }
	}
    }

    container interfaces-state {
	config "false";

	description
	    "Interface state information.";

	list interface {
	    key "name";

	    description
		"The list of interfaces on the device.";

	    leaf name {
		type string;
		description
		    "The name of the interface.";
	    }

	    leaf description {
		type string;
		description
		    "A textual description of the interface.";
	    }

	    leaf admin-status {
		type string;
		description
		    "The admin 'up' or 'down' status of the link.";
	    }

	    leaf link-status {
		type string;
		description
		    "The 'up' or 'down' status of the link.";
	    }

	    leaf link-speed {
		type uint32;
		description
		    "The link speed in kbps.";
	    }

	    leaf link-duplex {
		type string;
		description
		    "The link duplex, either 'half' or 'full'.";
	    }

	    leaf link-mtu {
		type uint16 {
		    range "0 | 68..max";
		}
		units octets;
		description
		    "The size, in octets, of the largest packet that the
		     interface will send and receive.";
	    }

	    leaf if-index {
		type int32;
		description
		    "The ifIndex value for the ifEntry represented by this
		     interface.";
		reference
		    "RFC 2863: The Interfaces Group MIB - ifIndex";
	    }

	    leaf mac-address {
		type yang:mac-address;
		description
		    "The Media Access Control (MAC) address of the
		    interface.";
	    }

	    leaf vrf {
		type ngcom:rt-identifier-63;
		description
		    "If present, this is the name of the Route Table
		     to which this interface is bound.  If not present,
		     the IF uses the Default Route Table.";
	    }

	    container ipv4 {
		presence
		    "Enables IPv4'";
		description
		    "IPv4 address family state information.";

		container address {
		    leaf-list ip {
			type inet:ipv4-prefix;
			description
			    "An IPv4 address on the interface.";
		    }
		}

		leaf mtu {
		    type uint16 {
			range "0 | 68..max";
		    }
		    units "octets";
		    description
			"The size, in octets, of the largest IPv4 packet that
			 the interface will send and receive.";
		}

		container tcp {
		    description
			"IPv4 TCP values.";

		    container mss {
			description
			    "IPv4 TCP Maximum Segment Size values.";

			leaf value {
			    type uint16;
			    units "octets";
			    description
				"The IPv4 TCP maximum segment size.";
			}

			leaf directions {
			    type mss-clamp-direction;
			    description
				"The directions to which the MSS applies.";
			}
		    }
		}

		leaf unnumbered {
		    type string;
		    description
			"This interface this interfaces is associated with.";
		}
	    }

	    container ipv6 {
		presence
		    "Enables IPv6";
		description
		    "IPv6 address family state information.";

		container address {
		    leaf-list ip {
			type inet:ipv6-prefix;
			description
			    "An IPv6 address on the interface.";
		    }
		}

		leaf mtu {
		    type uint32 {
			range "0 | 1280..max";
		    }
		    units "octets";
		    description
			"The size, in octets, of the largest IPv6 packet that
			 the interface will send and receive.";
		}

		container tcp {
		    description
			"IPv6 TCP values.";

		    container mss {
			description
			    "IPv6 TCP Maximum Segment Size values.";

			leaf value {
			    type uint16;
			    units "octets";
			    description
				"The IPv6 TCP maximum segment size.";
			}

			leaf directions {
			    type mss-clamp-direction;
			    description
				"The directions to which the MSS applies.";
			}
		    }
		}
	    }

	    container subif {
		description
		    "These fields all contribute to the subinterface
		     definition for VLAN handling.";

		leaf subid {
		    type uint32 {
			range "0..4294967294";
		    }
		    description
			"The subinterface id.  It is often also the (outer)
			 VLAN tag value, though they can be different.";
		}

		leaf dot1ad {
		    type boolean;
		    description
			"By default the outer tag is dot1q.  If this
			 value is true, it is instead dot1ad.";
		}

		leaf dot1ah {
		    type boolean;
		    description
			"If true, it is dot1ah.";
		}

		leaf exact-match {
		    type boolean;
		    description
			"By default matching is non-exact.  If this
			 value is true, matching is exact.";
		}

		leaf default {
		    type boolean;
		    description
			"The default subinterface is associated with a
			 packet that did not match any other configured
			 subinterface on this interface.";
		}

		leaf number-of-tags {
		    type uint8 {
			range "0..2";
		    }
		    description
			"The number of VLAN tags.";
		}

		leaf outer-vlan-id {
		    type intf-vlan-id;
		    description
			"The outer vlan tag id.  It can be an integer
			 between 1 and 4095 inclusive, or the word 'any'.";
		}

		leaf inner-vlan-id {
		    type intf-vlan-id;
		    description
			"The inner vlan tag id.  It can be an integer
			 between 1 and 4095 inclusive, or the word 'any'.";
		}
	    }

	    container counters {
		description
		    "Per-interface counters from VPP.";

		leaf collect-time {
		    type uint64;
		    description
			"time counters cleared in seconds since
			 midnight 1/1/1970 UTC";
		}

		leaf reset-time {
		    type uint64;
		    description
			"time counters reset in seconds since
			 midnight 1/1/1970 UTC";
		}

		leaf detailed-counters {
		    type boolean;
		    description
			"true if detailed counters are enabled";
		}

		leaf rx-bytes {
		    type uint64;
		    description
			"The number of octets received on this interface.";
		}

		leaf rx-packets {
		    type uint64;
		    description
			"The number of packets received on this interface.";
		}

		leaf rx-unicast-bytes {
		    type uint64;
		    description
			"The number of unicast octets received on this
			 interface.";
		}

		leaf rx-unicast-packets {
		    type uint64;
		    description
			"The number of unicast packets received on
			 this interface.";
		}

		leaf rx-multicast-bytes {
		    type uint64;
		    description
			"The number of multicast octets received on
			 this interface.";
		}

		leaf rx-multicast-packets {
		    type uint64;
		    description
			"The number of multicast packets received on
			 this interface.";
		}

		leaf rx-broadcast-bytes {
		    type uint64;
		    description
			"The number of broadcast octets received on
			 this interface.";
		}

		leaf rx-broadcast-packets {
		    type uint64;
		    description
			"The number of unicast packets received on
			 this interface.";
		}

		leaf rx-ip4 {
		    type uint64;
		    description
			"The number of IPv4 packets received on this
			 interface.";
		}

		leaf rx-ip6 {
		    type uint64;
		    description
			"The number of IPv6 packets received on this
			 interface.";
		}

		leaf rx-mpls {
		    type uint64;
		    description
			"The number of MPLS packets received on this
			 interface.";
		}

		leaf tx-bytes {
		    type uint64;
		    description
			"The number of octets transmitted on this interface.";
		}

		leaf tx-packets {
		    type uint64;
		    description
			"The number of packets transmitted on this interface.";
		}

		leaf tx-unicast-bytes {
		    type uint64;
		    description
			"The number of unicast octets transmitted on
			 this interface.";
		}

		leaf tx-unicast-packets {
		    type uint64;
		    description
			"The number of unicast packets transmitted on
			 this interface.";
		}

		leaf tx-multicast-bytes {
		    type uint64;
		    description
			"The number of multicast octets transmitted on
			 this interface.";
		}

		leaf tx-multicast-packets {
		    type uint64;
		    description
			"The number of multicast packets transmitted
			 on this interface.";
		}

		leaf tx-broadcast-bytes {
		    type uint64;
		    description
			"The number of broadcast octets transmitted on
			 this interface.";
		}

		leaf tx-broadcast-packets {
		    type uint64;
		    description
			"The number of broadcast packets transmitted
			 on this interface.";
		}

		leaf rx-error {
		    type uint64;
		    description
			"The number of receive errors on this interface.";
		}

		leaf tx-error {
		    type uint64;
		    description
			"The number of transmit errors on this interface.";
		}

		leaf drop {
		    type uint64;
		    description
			"The number of packet drops on this interface.";
		}

		leaf punt {
		    type uint64;
		    description
			"The number of punts on this interface.";
		}

		leaf rx-miss {
		    type uint64;
		    description
			"The number of receiver misses on this interface.";
		}

		leaf rx-no-buffer {
		    type uint64;
		    description
			"The number of packets dropped due to no receive
			 buffers on this interface.";
		}

    		leaf rx-bits-average {
    		    type uint64;
    		    description
    			"The average number of bits/second received over
    			 the last five minutes.";
    		}
    
    		leaf rx-packets-average {
    		    type uint64;
    		    description
    			"The average number of packets/second received over
    			 the last five minutes.";
    		}
    
    		leaf tx-bits-average {
    		    type uint64;
    		    description
    			"The average number of bits/second sent over
    			 the last five minutes.";
    		}
    
    		leaf tx-packets-average {
    		    type uint64;
    		    description
    			"The average number of packets/second sent over
    			 the last five minutes.";
    		}

	    }

	    container access-list {
		description
		    "If the interface has any Access Control Lists,
		     they are listed here in two groups: those that apply
		     to packet ingress and those that apply to egresss.
		     The two sets of ACLs are sorted independenty and
		     applied in ascending sequence-number order.";

		container input {
		    description
			"These are the ACL rule-sets that apply to ingress
			packets.";

		    list acl-list {
			key "sequence";
			description
			    "Each ACL rule-set can appear at most once within
			     the input list.";

			leaf sequence {
			    type uint32;
			    description
				"sequence number for ACL,";
			}

			leaf acl-name {
			    type string;
			    description
				"This is the name of an ACL rule-set
				 that will be be applied to packets on
				 this interface.";
			}
		    }
		}

		container output {
		    description
			"These are the ACL rule-sets that apply to egress
			 packets.";

		    list acl-list {
			key "sequence";
			description
			    "Each ACL rule-set can appear at most once within
			     the output list.";

			leaf sequence {
			    type uint32;
			    description
				"sequence number for ACL,";
			}

			leaf acl-name {
			    type string;
			    description
				"This is the name of an ACL rule-set
				 that will be be applied to packets on
				 this interface.";
			}
		    }
		}

		container macip {
		    description
			"An interface may also have at most one ACL
			 based upon a combination of MAC address and
			 IP. If that ACL is present, it is always on
			 the ingress packets.";

		    leaf macip-name {
			type string;
			description
			    "This name references at most one MACIP ingress
			     rule-set from the ACL MACIP tables.";
		    }
		}
	    }

	    container bond {
		description
		    "If the interface is being used as a slave, this node
		     contains the corresponding bond interface.";

		leaf if-name {
		    type ngcom:if-identifier-63;
		    description
			"The name of the bond interface.";
		}
	    }

	    container slave-if-table {
		description
		    "If the interface is a bond interface, this node
		     contains the list of its slave interfaces.";

		list slave-if {
		    key "if-name";
		    description
			"Slave interface.";

		    leaf if-name {
			type ngcom:if-identifier-63;
			description
			    "The name of the slave interface.";
		    }
		}
	    }

	    container vlan-tag-rewrite {
		leaf operation {
		    type intf-tag-rewrite-op;
		    description
			"A tag rewrite operation is one of the strings:
			 'disable', 'pop-1', 'pop-2', 'push-1', 'push-2',
			 'translate-1-1', 'translate-1-2',
			 'translate-2-1', 'translate-2-2'.";
		}

		leaf push-dot1q {
		    type boolean;
		    description
			"If true the first pushed tag is of type dot1q,
			 otherwise it will be of type dot1ad.";
		}

		leaf tag1 {
		    type uint32;
		    description
			"The first pushed tag value.";
		}

		leaf tag2 {
		    type uint32;
		    description
			"The second pushed tag value.";
		}
	    }
	}

	container bridge-table {
	    description
		"Bridge mapping table.";

	    list bridge-entry {
		key "bdi";
		description
		    "Bridge Domain Id.";

		leaf bdi {
		    type uint32 {
			range "1..16777215";
		    }
		    mandatory true;
		    description
			"The Bridge Domain Identifier.	A unique number
			 for this entry.";
		}

		leaf description {
		    type string {
			length "1..63";
		    }
		    description
			"A textual description of the bridge.";
		}

		leaf flood {
		    type boolean;
		    description
			"Broadcast/multicast flooding in the bd";
		}

		leaf uu-flood {
		    type boolean;
		    description
			"Unknown unicast flood in the bd";
		}

		leaf forward {
		    type boolean;
		    description
			"Forwarding on all interfaces in the bd";
		}

		leaf learn {
		    type boolean;
		    description
			"Learning on all interfaces in the bd";
		}

		leaf arp-term {
		    type boolean;
		    description
			"ARP termination in the bd";
		}

		leaf mac-age {
		    type uint8;
		    description
			"MAC aging time in min, 0 for disabled.";
		}

		leaf bvi-if-name {
		    type ngcom:if-identifier-63;
		    description
			"Bridge virtual interface name.";
		}

		container domain-if-members {
		    description
			"Bridge Domain Interface Members.";

		    list domain-if {
			key "if-name";
			description
			    "Bridge domain interface members.";

			leaf if-name {
			    type ngcom:if-identifier-63;
			    description
				"The name of an interface that is a
				 member of this bridge domain.";
			}

			leaf shg {
			    type string;
			    description
				"The split horizon group ID to which
				 this interface belongs.";
			}
		    }
		}

		container bridge-arp-table {
		    description
			"Bridge ARP Entry Table.";

		    list bridge-arp-entry {
			key "ip-address";
			description
			    "Bridge ARP entry table.";

			leaf ip-address {
			    type inet:ip-address-no-zone;
			    description
				"The IPv4 or IPv6 address of an ARP entry.";
			}

			leaf mac-address {
			    type yang:mac-address;
			    description
				"The MAC address of an ARP entry.";
			}
		    }
		}
	    }
	}

	container loopback-table {
	    description
		"Loopback name table.";

	    list loopback {
		key "name";
		description
		    "Loopback name.";

		leaf name {
		    type loopback-name-63;
		    description
			"The identifier.  A unique name
			 for this Loopback entry.";
		}

		leaf instance {
		    type uint16;
		    description
			"Each Loopback creates an interface.
			 The interface will be named 'loopback<X>',
			 where the <X> is the instance number.
			 The instance number must be unique
			 across all Loopback interfaces.";
		}

		leaf mac-address {
		    type yang:mac-address;
		    description
			"The MAC address for the interface.";
		}

		leaf description {
		    type string;
		    description
			"A user description of the Loopback.";
		}
	    }
	}

	container socket-table {
	    description
		"Host memif socket table.";

	    list socket {
		key "id";
		description
		    "A unique 32-bit integer identifying this socket
		     filename.";

		leaf id {
		    type uint32;
		    description
			"This is the user assigned id of the socket
			 filename.";
		}
		leaf filename {
		    type string;
		    mandatory true;
		    description
			"The path to a socket file used for establishing
			 memif connections.  A socket can be used for
			 either server or client interfaces, but not both.
			 A socket can have more than one server using it,
			 or it can have more than one client using it.";
		}
	    }
	}

	container memif-table {
	    description
		"Host memif interface state table.";

	    list memif-entry {
		key "socket-id memif-id";
		description
		    "A unique 32-bit integer identifying this interface.";

		leaf socket-id {
		    type uint32;
		    description
			"The id of a memif socket filename.";
		}

		leaf memif-id {
		    type uint32;
		    description
			"This is the user assigned id of the memif
			 interface.";
		}

		leaf admin-up {
		    type boolean;
		    description
			"If true the interface is administratively 'up'.";
		}

		leaf buffer-size {
		    type uint32;
		    description
			"The size of the buffer allocated for each
			 ring entry.  Default 2048.";
		}

		leaf if-name {
		    type ngcom:if-identifier-63;
		    description
			"The name of the corresponding interface.";
		}

		leaf link-up {
		    type boolean;
		    description
			"If true the interface is link is 'up'.";
		}

		leaf mac-address {
		    type yang:mac-address;
		    description
			"The MAC address of the interface.";
		}

		leaf memif-name {
		    type ngcom:if-identifier-63;
		    description
			"The name of memif interface.";
		}

		leaf mode {
		    type string;
		    description
			"Should be 'ethernet', 'IP' or 'punt/inject'.";
		}

		leaf ring-size {
		    type uint32;
		    description
			"The number of entries in the rx/tx rings.
			 The number of entries must be a power of 2
			 This number is that power of 2, between 8 and 32.
			 The default is 10, for 1024 entries.";
		}

		leaf role {
		    type string;
		    description
			"Should be 'server', or 'client'.";
		}
	    }
	}

	container tap-table {
	    description
		"Host Tap table.";

	    list tap {
		key "host-name";
		description
		    "Unique identifing host tap name.";

		leaf host-name {
		    type string;
		    description
			"The name of the tap on the host system.";
		}

		leaf host-bridge {
		    type string;
		    description
			"The host bridge to which the tap will be attached.";
		}

		leaf host-ipv4-prefix {
		    type inet:ipv4-prefix;
		    description
			"The IPv4 prefix on the interface.";
		}

		leaf host-ipv6-prefix {
		    type inet:ipv6-prefix;
		    description
			"The IPv6 prefix on the interface.";
		}

		leaf host-mac-address {
		    type yang:mac-address;
		    description
			"The MAC address of the host tap interface.";
		}

		leaf host-namespace {
		    type ngcom:network-namespace;
		    description
			"The host namespace in which the tap will be made.";
		}

		leaf instance {
		    type uint32 {
			range "0..8192";
		    }
		    description
			"The tap instance number.";
		}

		leaf rx-ring-size {
		    type uint8 {
			range "0..15";
		    }
		    description
			"A power of 2 between 0 and 15 inclusive yielding
			 a receive ring size 32 to 32768 entries.  The
			 default is 8 (256 entries).";
		}

		leaf tx-ring-size {
		    type uint8 {
			range "0..15";
		    }
		    description
			"A power of 2 between 0 and 15 inclusive yielding
			 a transmit ring size 32 to 32768 entries.  The
			 default is 8 (256 entries).";
		}
	    }
	}

	container bond-table {
	    description
		"Bond interface state table.";

	    list bond {
		key "instance";
		description
		    "Bond interface.";

		leaf instance {
		    type uint32;
		    description
			"The identifier. A unique number
			 for this bond interface.";
		}

		leaf if-name {
		    type ngcom:if-identifier-63;
		    description
			"The name of the bond interface.";
		}

		leaf mode {
		    type bond-mode;
		    mandatory true;
		    description
			"The mode for the interface.";
		}

		leaf mac-address {
		    type yang:mac-address;
		    description
			"The MAC address for the interface.";
		}

		leaf load-balance {
		    type bond-load-balance;
		    default l2;
		    description
			"The load balance for the interface.";
		}

		leaf active-slaves {
		    type uint32;
		    description
			"The number of active slaves.";
		}

		leaf slaves {
		    type uint32;
		    description
			"The total number of slaves.";
		}

		container slave-if-table {
		    description
			"The list of slave interfaces.";

		    list slave-if {
			key "if-name";
			description
			    "Slave interface.";

			leaf if-name {
			    type ngcom:if-identifier-63;
			    description
				"The name of a slave interface.";
			}

			leaf passive {
			    type boolean;
			    default false;
			    description
				"The slave interface does not
				 initiate the LACP protocol,
				 remote must be active speaker.";
			}

			leaf long-timeout {
			    type boolean;
			    default false;
			    description
				"90 seconds VS default 3 seconds
				 neighbor timeout.";
			}
		    }
		}
	    }
	}

	container lacp-table {
	    description
		"Link Aggregation Control Protocol (LACP)
		 state table.";

	    list lacp-entry {
		key "slave-if-name";
		description
		    "LACP entry.";

		leaf slave-if-name {
		    type ngcom:if-identifier-63;
		    description
			"The name of the slave interface.";
		}

		leaf rx-state {
		    type lacp-rx-state;
		    description
			"The RX machine state for the interface.";
		}

		leaf tx-state {
		    type lacp-tx-state;
		    description
			"The TX machine state for the interface.";
		}

		leaf mux-state {
		    type lacp-mux-state;
		    description
			"The MUX machine state for the interface.";
		}

		leaf ptx-state {
		    type lacp-ptx-state;
		    description
			"The PTX machine state for the interface.";
		}

		leaf bond-if-name {
		    type ngcom:if-identifier-63;
		    description
			"The name of the bond interface.";
		}

		container actor {
		    description
			"The actor parameters.";

		    leaf system-priority {
			type uint16;
			description
			    "The actor system priority.";
		    }

		    leaf system {
			type yang:mac-address;
			description
			    "The actor system.";
		    }

		    leaf key {
			type uint16;
			description
			    "The actor key.";
		    }

		    leaf port-priority {
			type uint16;
			description
			    "The actor port priority.";
		    }

		    leaf port-number {
			type uint16;
			description
			    "The actor port number.";
		    }

		    leaf state {
			type uint8;
			description
			    "The actor state.";
		    }
		}

		container partner {
		    description
			"The partner parameters.";

		    leaf system-priority {
			type uint16;
			description
			    "The partner system priority.";
		    }

		    leaf system {
			type yang:mac-address;
			description
			    "The partner system.";
		    }

		    leaf key {
			type uint16;
			description
			    "The partner key.";
		    }

		    leaf port-priority {
			type uint16;
			description
			    "The partner port priority.";
		    }

		    leaf port-number {
			type uint16;
			description
			    "The partner port number.";
		    }

		    leaf state {
			type uint8;
			description
			    "The partner state.";
		    }
		}
	    }
	}
    }
}
