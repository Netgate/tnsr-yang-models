module netgate-neighbor {

    yang-version 1.1;

    namespace "urn:netgate:xml:yang:netgate-neighbor";
    prefix "ngneigh";

    import ietf-inet-types {
	prefix "inet";
    }

    import ietf-yang-types {
	prefix "yang";
    }

    import netgate-cli-extensions {
	prefix "ngcliext";
    }

    import netgate-common {
	prefix "ngcom";
    }

    organization "Netgate";

    contact "Web: <http://www.netgate.com>";

    description
	"This YANG module provides a Netgate-defined data-model
	 for neighbor data.

	 Copyright 2017-2020 Rubicon Communications, LLC.";

    revision 2023-11-01 {
	description
	    "TNSR Release 23.11.";
    }

    revision 2021-02-15 {
	description
	    "TNSR Release 21.02.";
    }

    revision 2020-06-15 {
	description
	    "TNSR Release 20.06.";
    }

    revision 2020-02-15 {
	description
	    "TNSR Release 20.02.";
    }

    revision 2019-02-15 {
	description
	    "TNSR Release 19.02.";
    }

    revision 2017-11-06 {
	description
	    "Initial revision.";
    }

    grouping neighbor-cache-options-config {
	description
	    "Group of attributes for neighbor cache options state.";

	leaf max-number {
	    type uint32 {
		range "1..max";
	    }
	    default 50000;
	    description
		"The maximum number of neighbors that can be stored in
		 the cache.";
	    ngcliext:node-fmt "$< $% @@$n";
	}

	leaf max-age {
	    type uint32;
	    units "seconds";
	    default 300;
	    description
		"The maximum age (in seconds) before an inactive neighbor
		 is removed from the cache. When zero, aging is disabled.";
	    ngcliext:node-fmt "$< $% @@$n";
	}
    }

    grouping neighbor-cache-options-state {
	description
	    "Group of attributes for neighbor cache options state.";

	leaf max-number {
	    type uint32;
	    description
		"The maximum number of neighbors that can be stored in
		 the cache.";
	}

	leaf max-age {
	    type uint32;
	    units "seconds";
	    description
		"The maximum age (in seconds) before an inactive neighbor
		 is removed from the cache. When zero, aging is disabled.";
	}

	leaf recycle {
	    type boolean;
	    description
		"If true, the oldest neighbor will be recycled when maximum
		 number of neighbors is reached and new ones need to be
		 created.";
	}
    }

    container "neighbor-config" {
	description
	    "Neighbor configuration data.";

	ngcliext:parent-fmt "neighbor";

	container neighbor-table {
	    description
		"Neighbor mapping table.";

	    ngcliext:parent-fmt "$<";

	    list interface {
		key "if-name";
		description
		    "Neighbor table entry.";

		ngcliext:parent-fmt "$< @{if-name}";

		leaf if-name {
		    type ngcom:if-identifier-63;
		    description
			"The interface on which the neighbor entry is found.";
		}

		container neighbors {
		    description
			"Addresses for which there is a neighbor Entry.";

		    ngcliext:parent-fmt "$<";

		    list neighbor-entry {
			key "ip-address";
			description
			    "Neighbor entry table.";

			ngcliext:node-fmt "$< ";
			ngcliext:children-order "ip-address
			    mac-address
			    is-no-route-table-entry";
			ngcliext:post-node-fmt "$n";

			leaf ip-address {
			    type inet:ip-address-no-zone;
			    description
				"The IP address whose MAC address is stated.";
			    ngcliext:node-fmt "@@ ";
			}

			leaf mac-address {
			    type yang:mac-address;
			    description
				"The MAC address of an neighbor entry.";
			    ngcliext:node-fmt "@@";
			}

			leaf is-no-route-table-entry {
			     type boolean;
			     description
				"True if this neighbor entry is shoud have no
				 entry made in the adjacency route table.";
			    ngcliext:node-op "bool";
			    ngcliext:node-fmt "| no-adj-route-table-entry";
			}
		    }
		}
	    }
	}

	container neighbor-cache-options {
	    description
		"Neighbor cache options.";

	    ngcliext:parent-fmt "$< cache-options";

	    container ipv4 {
		description
		    "IPv4 neighbor cache options.";

		ngcliext:parent-fmt "$< $%";

		uses neighbor-cache-options-config;
	    }

	    container ipv6 {
		description
		    "IPv6 neighbor cache options.";

		ngcliext:parent-fmt "$< $%";

		uses neighbor-cache-options-config;
	    }
	}
    }

    container "neighbor-state" {
	config "false";

	description
	    "Neighbor state data.";

	container neighbor-table {
	    description
		"Neighbor mapping table.";

	    list interface {
		key "if-name";
		description
		    "Neighbor table entry.";

		leaf if-name {
		    type ngcom:if-identifier-63;
		    description
			"The interface on which the neighbor entry is found.";
		}

		container neighbors {
		    description
			"Addresses for which there is a neighbor Entry.";

		    list neighbor-entry {
			key "ip-address";
			description
			    "Neighbor entry table.";

			leaf ip-address {
			    type inet:ip-address-no-zone;
			    description
				"The IP address whose MAC address is stated.";
			}

			leaf mac-address {
			    type yang:mac-address;
			    description
				"The MAC address of an neighbor entry.";
			}

			leaf is-static {
			     type boolean;
			     description
				"True if this neighbor entry is static.";
			}

			leaf age {
			    type uint32;
			    description
			        "Age of neighbor";
			}
		    }
		}
	    }
	}

	container neighbor-cache-options {
	    description
		"Neighbor cache options.";

	    container ipv4 {
		description
		    "IPv4 neighbor cache options.";

		uses neighbor-cache-options-state;
	    }

	    container ipv6 {
		description
		    "IPv6 neighbor cache options.";

		uses neighbor-cache-options-state;
	    }
	}
    }
}
