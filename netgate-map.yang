module netgate-map {

    yang-version 1.1;

    namespace "urn:netgate:xml:yang:netgate-map";
    prefix "ngmap";

    import clixon-lib {
	prefix "cl";
    }

    import ietf-inet-types {
	prefix "inet";
    }

    import netgate-cli-extensions {
	prefix "ngcliext";
    }

    import netgate-common {
	prefix "ngcom";
    }

    organization "Netgate";

    contact "Web: <http://www.netgate.com>";

    description
	"This YANG module provides a Netgate-defined data-model
	 for Mapping Address and Port (MAP) data.

	 Copyright 2018-2022, 2025 Rubicon Communications, LLC.
	 ";

    revision 2025-10-15 {
	description
	    "TNSR Release 25.10.";
    }

    revision 2025-02-01 {
	description
	    "TNSR Release 25.02.";
    }

    revision 2022-02-15 {
	description
	    "TNSR Release 22.02.";
    }

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-02-15 {
	description
	    "TNSR Release 19.02.";
    }

    revision 2018-11-13;

    container nat64-config {

	container map {
	    description
		"Configuration for MAP-E and MAP-t translations.";

	    ngcliext:parent-fmt "map";

	    container parameters {
		description
		    "Global MAP parameters.";

		ngcliext:node-fmt "$< $%$n";
		ngcliext:pre-children-op "push";

		container fragment {
		    description
			"Parameters that indicate how MAP fragmentation
			 should happen.";

		    ngcliext:parent-fmt "^fragment";

		    leaf inner {
			type boolean;
			description
			    "If needed, inner packets should be fragmented.";
			ngcliext:node-op "bool";
			ngcliext:node-fmt "$< outer$n|$< inner$n";
		    }

		    leaf ignore-df {
			type boolean;
			description
			    "If true, perform IPv4 fragmentation despite the
			     value of the DF bit.";
			ngcliext:node-op "bool";
			ngcliext:node-fmt "|$< $%$n";
		    }
		}

		container icmp {
		    description
			"MAP ICMP parameters.";

		    leaf source-address {
			type inet:ipv4-address-no-zone;
			description
			    "This parameter specifies the ICMP error relay
			     source address.";
			ngcliext:node-fmt "^icmp $% @@$n";
		    }
		}

		container icmp6 {
		    description
			"MAP ICMP6 parameters.";

		    leaf unreachables {
			type boolean;
			description
			    "If true, generate ICMP6 unreachable messages.";
			ngcliext:node-op "bool";
			ngcliext:node-fmt "|^icmp6 unreachable-msgs enable$n";
		    }
		}

		container tcp {
		    description
			"MAP TCP parameters.";

		    leaf mss {
			type uint16;
			description
			    "The Maximum Segment Size is the largest
			     amount of data, specified in bytes, that TCP
			     is willing to receive in a single segment.";
			ngcliext:node-fmt "^tcp $% @@$n";
		    }
		}

		container pre-resolve {
		    description
			"MAP pre-resolved routing parameters.";

		    container ipv4 {
			description
			    "IPv4 pre-resolved parameters.";

			leaf next-hop {
			    type inet:ipv4-address-no-zone;
			    description
				"Use this IPv4 as the re-resolved next-hop.";
			    ngcliext:node-fmt "^pre-resolve ipv4 $% @@$n";
			}
		    }

		    container ipv6 {
			description
			    "IPv6 pre-resolved parameters.";

			leaf next-hop {
			    type inet:ipv6-address-no-zone;
			    description
				"Use this IPv6 as the re-resolved next-hop.";
			    ngcliext:node-fmt "^pre-resolve ipv6 $% @@$n";
			}
		    }
		}

		container security-check {
		    description
			"MAP security-check parameters.";

		    leaf enable {
			type boolean;
			default true;
			description
			    "If true, perform security checks on the first
			     inbound packet.";
			ngcliext:node-op "bool";
			ngcliext:node-fmt "|^security-check enable$n";
		    }

		    leaf fragments {
			type boolean;
			description
			    "If true, also perform security checks on the
			     subsequent inbound fragments too.";
			ngcliext:node-op "bool";
			ngcliext:node-fmt "|^security-check $% enable$n";
		    }
		}

		container traffic-class {
		    description
			"MAP traffic-class parameters.";

		    leaf copy {
			type boolean;
			description
			    "If true, the traffic class/TOS field is
			     copied from the original packet to the
			     encapsulating header.  If false, the 'tc'
			     value is encoded instead.";
			ngcliext:node-op "bool";
			ngcliext:node-fmt "|^traffic-class $% enable$n";
		    }

		    leaf tc {
			type uint8;
			description
			    "If the 'copy' field is false, encode this value
			     as the traffic-class/TOS field in encapsulated
			     headers.";
			ngcliext:node-fmt "^traffic-class tc @@$n";
		    }
		}
	    }

	    container map-domains {
		description
		    "MAP table.";

		ngcliext:parent-fmt "$<";

		list domain {
		    key "name";
		    description
			"MAP domain name.";

		    ngcliext:node-fmt "$< @{name}$n";
		    ngcliext:pre-children-op "push";

		    leaf name {
			type ngcom:identifier-63;
			description
			    "The unique MAP domain name identifier.";
		    }

		    leaf description {
			type ngcom:description-63;
			description
			    "An arbitrary description of the MAP domain.";
			ngcliext:node-fmt "^$% @@$n";
			cl:ignore-compare;
		    }

		    leaf ip4-prefix {
			 type inet:ipv4-prefix;
			 description
			    "The Rule IPv4 prefix.";
			ngcliext:node-fmt "^ipv4 prefix @@$n";
		    }

		    leaf ip6-prefix {
			 type inet:ipv6-prefix;
			 description
			    "The Rule IPv6 prefix.";
			ngcliext:node-fmt "^ipv6 prefix @@$n";
		    }

		    leaf ip6-src-prefix {
			 type inet:ipv6-prefix;
			 description
			    "The IPv6 Border Relay (BR) address or
			     tunnel source.  For MAP-E, this prefix
			     must be a full /128 address.  For MAP-T,
			     this prefix must be /96 or /64.";
			ngcliext:node-fmt "^ipv6 source @@$n";
		    }

		    leaf ea-bits-length {
			type uint8 {
			    range "0..128";
			}
			description
			    "The width of the embedded address field in bits.";
			ngcliext:node-fmt "^embedded-address bit-length @@$n";
		    }

		    leaf psid-offset {
			type uint8 {
			    range "0..64";
			}
			description
			    "The offset of the Port Set Identifier (PSID).";
			ngcliext:node-fmt "^port-set offset @@$n";
		    }

		    leaf psid-length {
			type uint8 {
			    range "0..64";
			}
			description
			    "The length of the Port Set Identifier (PSID).";
			ngcliext:node-fmt "^port-set length @@$n";
		    }

		    leaf mtu {
			type uint16;
			description
			    "MTU";
			ngcliext:node-fmt "^$% @@$n";
		    }

		    container rules {
			description
			    "The set of MAP Rules.";

			list rule {
			    key "psid";
			    description
				"Port Set Identifier";

			    ngcliext:node-fmt "^$% port-set @{psid} ipv6-destination @{ip6-destination}$n";

			    leaf psid {
				type uint32;
				description
				    "The PSID in the range
				     [0 .. (1 << psid-length)).";
			    }

			    leaf ip6-destination {
				 type inet:ipv6-address;
				 description
				    "The destination IPv6 address.";
			    }
			}
		    }
		}
	    }
	}
    }

    container nat64-state {

	container map {
	    config "false";

	    description
		"State for MAP-E and MAP-t translations.";

	    container parameters {
		description
		    "Global MAP parameters.";

		container fragment {
		    description
			"Parameters that indicate how MAP fragmentation
			 should happen.";

		    leaf inner {
			type boolean;
			description
			    "If needed, inner packets should be fragmented.";
		    }

		    leaf ignore-df {
			type boolean;
			description
			    "If true, perform IPv4 fragmentation despite the
			     value of the DF bit.";
		    }
		}

		container icmp {
		    description
			"MAP ICMP parameters.";

		    leaf source-address {
			type inet:ipv4-address-no-zone;
			description
			    "This parameter specifies the ICMP error relay
			     source address.";
		    }
		}

		container icmp6 {
		    description
			"MAP ICMP6 parameters.";

		    leaf unreachables {
			type boolean;
			description
			    "If true, generate ICMP6 unreachable messages.";
		    }
		}

		container tcp {
		    description
			"MAP TCP parameters.";

		    leaf mss {
			type uint16;
			description
			    "The Maximum Segment Size is the largest
			     amount of data, specified in bytes, that TCP
			     is willing to receive in a single segment.";
		    }
		}

		container pre-resolve {
		    description
			"MAP pre-resolved routing parameters.";

		    container ipv4 {
			description
			    "IPv4 pre-resolved parameters.";

			leaf next-hop {
			    type inet:ipv4-address-no-zone;
			    description
				"Use this IPv4 as the re-resolved next-hop.";
			}
		    }

		    container ipv6 {
			description
			    "IPv6 pre-resolved parameters.";

			leaf next-hop {
			    type inet:ipv6-address-no-zone;
			    description
				"Use this IPv6 as the re-resolved next-hop.";
			}
		    }
		}

		container security-check {
		    description
			"MAP security-check parameters.";

		    leaf enable {
			type boolean;
			description
			    "If true, perform security checks on the first
			     inbound packet.";
		    }
		    leaf fragments {
			type boolean;
			description
			    "If true, also perform security checks on the
			     subsequent inbound fragments too.";
		    }
		}

		container traffic-class {
		    description
			"MAP traffic-class parameters.";

		    leaf copy {
			type boolean;
			description
			    "If true, the traffic class/TOS field is
			     copied from the original packet to the
			     encapsulating header.  If false, the 'tc'
			     value is encoded instead.";
		    }
		    leaf tc {
			type uint8;
			description
			    "If the 'copy' field is false, encode this value
			     as the traffic-class/TOS field in encapsulated
			     headers.";
		    }
		}
	    }

	    container map-domains {
		description
		    "MAP table.";

		list domain {
		    key "name";
		    description
			"MAP domain name.";

		    leaf name {
			type ngcom:identifier-63;
			description
			    "The unique MAP domain name identifier.";
		    }

		    leaf description {
			type string;
			description
			    "An arbitrary description of the MAP domain.";
		    }

		    leaf ip4-prefix {
			 type inet:ipv4-prefix;
			 description
			    "The Rule IPv4 prefix.";
		    }

		    leaf ip6-prefix {
			 type inet:ipv6-prefix;
			 description
			    "The Rule IPv6 prefix.";
		    }

		    leaf ip6-src-prefix {
			 type inet:ipv6-prefix;
			 description
			    "The IPv6 Border Relay (BR) address or
			     tunnel source.  For MAP-E, this prefix
			     must be a full /128 address.  For MAP-T,
			     this prefix must be /96 or /64.";
		    }

		    leaf ea-bits-length {
			type uint8 {
			    range "0..128";
			}
			description
			    "The width of the embedded address field in bits.";
		    }

		    leaf psid-offset {
			type uint8 {
			    range "0..64";
			}
			description
			    "The offset of the Port Set Identifier (PSID).";
		    }

		    leaf psid-length {
			type uint8 {
			    range "0..64";
			}
			description
			    "The length of the Port Set Identifier (PSID).";
		    }

		    leaf mtu {
			type uint16;
			description
			    "MTU";
		    }

		    container rules {
			description
			    "The set of MAP Rules.";

			list rule {
			    key "psid";
			    description
				"Port Set Identifier";

			    leaf psid {
				type uint32;
				description
				    "The PSID in the range
				     [0 .. (1 << psid-length)).";
			    }

			    leaf ip6-destination {
				 type inet:ipv6-address;
				 description
				    "The destination IPv6 address.";
			    }
			}
		    }
		}
	    }
	}
    }
}
