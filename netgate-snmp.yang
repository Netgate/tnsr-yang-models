module netgate-snmp {

    yang-version 1.1;

    namespace "https://netgate.com/ns/netgate-snmp";
    prefix "ngsnmp";

    import ietf-inet-types {
	prefix "inet";
    }

    import netgate-cli-extensions {
	prefix "ngcliext";
    }

    import netgate-common {
	prefix "ngcom";
    }

    organization "Netgate";

    contact "Web: <http://www.netgate.com>";

    description
	"This YANG module provides a data model for SNMP Services.

	 Copyright 2019-2020 Rubicon Communications, LLC.";

    revision 2022-02-15 {
	description
	    "TNSR Release 22.02.";
    }

    revision 2021-02-15 {
	description
	    "TNSR Release 21.02.";
    }

    revision 2020-06-15 {
	description
	    "TNSR Release 20.06.";
    }

    revision 2020-02-15 {
	description
	    "TNSR Release 20.02.";
    }

    revision 2019-12-15 {
	description
	    "TNSR Release 19.12.";
    }

    revision 2019-08-30 {
	description
	    "TNSR Release 19.08.";
    }


    typedef snmp-view-type {
	type enumeration {
	    enum included;
	    enum excluded;
	}
    }

    typedef snmp-security-level {
	type enumeration {
	    enum noauth;
	    /* enum auth; */
	    /* enum priv; */
	}
    }

    typedef snmp-security-model {
	type enumeration {
	    enum any;
	    enum v1;
	    enum v2c;
	    /* enum usm; */
	    /* enum tsm; */
	    /* enum ksm; */
	}
    }

    typedef snmp-context-match {
	type enumeration {
	    enum exact;
	    /* enum prefix; */
	}
    }

    typedef snmp-source {
	type union {
	    type enumeration { enum "default"; }
	    type inet:ipv6-prefix;
	    type inet:ipv4-prefix;
	}
    }

    rpc snmp-control {
        input {
	    leaf operation {
	        type ngcom:service-operation;
	        mandatory true;
	        description
                    "One of the strings 'start', 'stop', 'restart',
                     or 'status'.";
	    }

	    leaf namespace {
		type ngcom:network-namespace;
		description
		    "Network namespace.";
	    }
	}

	output {
	    leaf stdout {
		type string;
	    }
	}
    }

    rpc snmp-coredump {
        input {
            leaf operation {
                type ngcom:service-op-enable-disable;
                mandatory true;
                description
		    "One of the strings 'enable' or 'disable'.";
            }

	    leaf namespace {
		type ngcom:network-namespace;
		description
		    "Network namespace.";
	    }
        }

	output {
	    leaf stdout {
		type string;
	    }
	}
    }

    container snmp-config {

	description
	    "Simple Network Management Protocol (SNMP) configuration.";

	ngcliext:parent-fmt "snmp";

	leaf snmp-enable {
	    type boolean;
	    default "false";
	    description
		"Enable the SNMP daemons.";
	    ngcliext:node-op "bool";
	    ngcliext:node-fmt "$< host disable$n|$< host enable$n";
	}

	container dataplane {
	    description
		"Dataplane-specific parameters of SNMP server.";

	    ngcliext:parent-fmt "$< dataplane";

	    leaf enable {
		type boolean;
		description
		    "If true, SNMP server is enabled for dataplane
		    interfaces.";
		ngcliext:node-op "bool";
		ngcliext:node-fmt "$< disable$n|$< enable$n";
	    }
	}

	container snmp-access-control {

	    ngcliext:parent-fmt "$<";

	    list community-map {
		key "community-name";

		description
		    "Map community name from SNMP request to security name.";

		ngcliext:parent-fmt "$< community community-name @{community-name}";

		leaf community-name {
		    type string;
		    description
			"Community name.";
		}

		list map-entry {
		    key "context source";

		    ngcliext:node-fmt "$< source @{source} security-name @{security-name}$n";

		    leaf context {
			type string;
			description
			    "SNMPv3 context.";
		    }

		    leaf source {
			type snmp-source;
			description
			    "Host name or IP address for source host.";
		    }

		    leaf security-name {
			type string;
			mandatory true;
			description
			    "Security name.";
		    }
		}
	    }

	    list group {
		key "group-name";

		description
		    "Map security name to group.";

		ngcliext:parent-fmt "$< group group-name @{group-name}";

		leaf group-name {
		    type string;
		}

		list group-entry {
		    key "security-name security-model";

		    ngcliext:node-fmt "$< security-name @{security-name} security-model @{security-model}$n";

		    leaf security-name {
			type string;
		    }

		    leaf security-model {
			type snmp-security-model;
		    }
		}
	    }

	    list view {
		key "view-name";

		description
		    "Defines a subset of the OID tree.";

		ngcliext:parent-fmt "$< view view-name @{view-name}";

		leaf view-name {
		    type string;
		}

		list view-entry {
		    key "type oid";

		    ngcliext:node-fmt "$< view-type @{type} oid @{oid}$n";

		    leaf type {
			type snmp-view-type;
			description
			    "One of 'exclude' or 'include'.";
		    }

		    leaf oid {
			type ngcom:object-id-view-128;
			mandatory true;
			description
			    "SNMP OID.";
		    }

		    leaf mask {
			type string;
		    }
		}
	    }

	    list access {
		key "group-name";

		description
		    "Map from group to views.";

		ngcliext:parent-fmt "$< access group-name @{group-name}";

		leaf group-name {
		    type string;
		}

		list access-entry {
		    key "context prefix security-model security-level";

		    ngcliext:node-fmt "$< prefix @{prefix} model @{security-model} level @{security-level} read @{read} write @{write}$n";

		    leaf context {
			type string;
		    }

		    leaf prefix {
			type snmp-context-match;
		    }

		    leaf security-model {
			type snmp-security-model;
		    }

		    leaf security-level {
			type snmp-security-level;
		    }

		    leaf read {
			type string;
			mandatory true;
			description
			    "View to use for read ops.";
		    }

		    leaf write {
			type string;
			mandatory true;
			description
			    "View to use for write ops.";
		    }
		}
	    }
	}
    }
}
