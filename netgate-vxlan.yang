module netgate-vxlan {

    yang-version 1.1;

    namespace "urn:netgate:xml:yang:netgate-vxlan";
    prefix "ngvxlan";

    import ietf-inet-types {
	prefix "inet";
    }

    import netgate-cli-extensions {
	prefix "ngcliext";
    }

    import netgate-common {
	prefix "ngcom";
    }

    organization "Netgate";

    contact "Web: <http://www.netgate.com>";

    description
	"This YANG module provides a Netgate-defined data-model
	 for VXLAN data.

	 Copyright 2018-2020 Rubicon Communications, LLC. ";

    revision 2022-10-15 {
	description
	    "TNSR Release 22.10.";
    }

    revision 2021-06-15 {
	description
	    "TNSR Release 21.07.";
    }

    revision 2021-02-15 {
	description
	    "TNSR Release 21.02.";
    }

    revision 2020-10-15 {
	description
	    "TNSR Release 20.10.";
    }

    revision 2020-06-15 {
	description
	    "TNSR Release 20.06.";
    }

    revision 2020-02-15 {
	description
	    "TNSR Release 20.02.";
    }

    revision 2019-05-30 {
	description
	    "TNSR Release 19.05.";
    }

    revision 2019-02-15 {
	description
	    "TNSR Release 19.02.";
    }

    revision 2018-01-31 {
	description
	    "Initial revision.";
    }

    container "vxlan-config" {
	description
	    "Configuration for VXLAN tunnels.";

	container vxlan-table {
	    description
		"VXLAN table.";

	    list tunnel {
		key "name";
		description
		    "VXLAN tunnel name.";

		ngcliext:node-fmt "vxlan @{name}$n";
		ngcliext:pre-children-op "push";

		leaf name {
		    type ngcom:if-identifier-63;
		    description
			"The VXLAN tunnel identifier.  A unique name
			 for this VXLAN tunnel.";
		}

		leaf encap-route-table {
		    type ngcom:rt-identifier-63;
		    description
			"The name of an encapsulation route table.";
		    ngcliext:node-fmt "^encapsulation route-table @@$n";
		}

		leaf instance {
		    type uint32;
		    description
			"Each VXLAN creates an interface.  The created
			 interface will be named 'vxlan_tunnel<X>',
			 where the <X> is the instance number.  The
			 instance number must be unique across all
			 VXLAN entries.";
		    ngcliext:node-fmt "^$% @@$n";
		}

		leaf mcast-if-name {
		    type ngcom:if-identifier-63;
		    description
			"The interface to use, along with a multicast
			 destination IP address, if a multicast
			 destination is desired.";
		    ngcliext:node-fmt "^multicast-interface @@$n";
		}

		leaf vni {
		    type uint32 {
			range "0..16777215";
		    }
		    description
			"VNI value, u24.";
		    ngcliext:node-fmt "^vni @@$n";
		}

		leaf src-ip-address {
		     type inet:ip-address-no-zone;
		     description
			"The source IP address.";
		    ngcliext:node-fmt "^source @@$n";
		}

		leaf dst-ip-address {
		     type inet:ip-address-no-zone;
		     description
			"The destination IP address.";
		    ngcliext:node-fmt "^destination @@$n";
		}
	    }
	}
    }

    container "vxlan-state" {
	config "false";

	description
	    "State of the VXLAN tunnels.";

	container vxlan-table {
	    description
		"VXLAN table.";

	    list tunnel {
		key "name";
		description
		    "VXLAN tunnel name.";

		leaf name {
		    type ngcom:if-identifier-63;
		    description
			"The VXLAN tunnel identifier.  A unique name
			 for this VXLAN tunnel.";
		}

		leaf dst-ip-address {
		     type inet:ip-address-no-zone;
		     description
			"The destination IP address.";
		}

		leaf encap-route-table {
		    type ngcom:rt-identifier-63;
		    description
			"The name of an encapsulation route table.";
		}

		leaf if-name {
		    type ngcom:if-identifier-63;
		    description
			"The VXLAN tunnel interface name.";
		}

		leaf instance {
		    type uint32;
		    description
			"Each VXLAN creates an interface.  The created
			 interface will be named 'vxlan_tunnel<X>',
			 where the <X> is the instance number.  The
			 instance number must be unique across all
			 VXLAN entries.";
		}

		leaf mcast-if-name {
		    type ngcom:if-identifier-63;
		    description
			"The interface to use, along with a multicast
			 destination IP address, if a multicast
			 destination is desired.";
		}

		leaf src-ip-address {
		     type inet:ip-address-no-zone;
		     description
			"The source IP address.";
		}

		leaf vni {
		    type uint32 {
			range "0..16777215";
		    }
		    mandatory true;
		    description
			"VNI value, u24.";
		}

	    }
	}
    }
}
