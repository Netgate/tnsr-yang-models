module netgate-route {

    yang-version 1.1;

    namespace "urn:netgate:xml:yang:netgate-route";
    prefix "ngrt";

    organization "Netgate";

    contact "Web: <http://www.netgate.com>";

    description
        "Container for routing related YANG models.

         Consider carefully when modifying this file. It serves primarily
         as a point for the actual models for the routing to attach to
         via an augment statement.

         Copyright 2017-2020 Rubicon Communications, LLC. All rights reserved.";

    revision 2023-02-15 {
	description
	    "TNSR Release 23.02.";
    }

    revision 2022-10-15 {
	description
	    "TNSR Release 22.10.";
    }

    revision 2022-02-15 {
	description
	    "TNSR Release 22.02.";
    }

    revision 2020-06-15 {
	description
	    "TNSR Release 20.06.";
    }

    revision 2020-02-15 {
	description
	    "TNSR Release 20.02.";
    }

    revision 2019-02-15 {
	description
	    "TNSR Release 19.02.";
    }

    revision 2018-12-10 {
        description
            "Initial revision.";
    }

    container route-config {
	description
	    "Root container for routing models";

	container dynamic {
	}

	container static {
	}
    }

    container route-state {
	config "false";

	description
	    "Root container for routing models";

	container dynamic {
	}

	container static {
	}
    }
}
