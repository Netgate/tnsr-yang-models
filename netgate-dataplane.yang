module netgate-dataplane {

    yang-version 1.1;

    namespace "urn:netgate:xml:yang:netgate-dataplane";
    prefix "ngdataplane";

    import netgate-cli-extensions {
	prefix "ngcliext";
    }

    import netgate-common {
	prefix "ngcom";
    }

    organization "Netgate";

    contact "Web: <http://www.netgate.com>";

    description
	"This module defines startup configuration settings for VPP.

	 This includes items related to how VPP itself is run, such
	 as memory allocations, which devices to manage, which drivers
	 to use.

	 This does not include dataplane configurations such as the IP
	 address assigned to an interface or IP routes. 
	 to the underlying data-model elements for the Netgate router.

	 Copyright 2018-2020 Rubicon Communications, LLC.
	";

    revision 2026-10-02 {
	description
	    "Reject dpdk no-multi-seg with LRO or with MTUs that don't
	     fit into a single buffer.";
    }

    revision 2026-10-01 {
	description
	    "TNSR Release 26.10.";
    }

    revision 2025-10-01 {
	description
	    "TNSR Release 25.10.";
    }

    revision 2025-06-01 {
	description
	    "TNSR Release 25.06.";
    }

    revision 2025-02-01 {
	description
	    "TNSR Release 25.02.";
    }

    revision 2024-02-02 {
	description
	    "TNSR Release 24.02.";
    }

    revision 2023-11-01 {
	description
	    "TNSR Release 23.11.";
    }

    revision 2023-06-01 {
	description
	    "TNSR Release 23.06.";
    }

    revision 2023-02-01 {
	description
	    "TNSR Release 23.02.";
    }

    revision 2022-10-15 {
	description
	    "TNSR Release 22.10.";
    }

    revision 2022-06-15 {
	description
	    "TNSR Release 22.06.";
    }

    revision 2022-02-15 {
	description
	    "TNSR Release 22.02.";
    }

    revision 2021-11-15 {
	description
	    "TNSR Release 21.11.";
    }

    revision 2021-06-15 {
	description
	    "TNSR Release 21.07.";
    }

    revision 2021-02-15 {
	description
	    "TNSR Release 21.02.";
    }

    revision 2020-11-01 {
	description
	    "TNSR Release 20.10.1";
    }

    revision 2020-10-15 {
	description
	    "TNSR Release 20.10.";
    }

    revision 2020-06-15 {
	description
	    "TNSR Release 20.06.";
    }

    revision 2020-02-15 {
	description
	    "TNSR Release 20.02.";
    }

    revision 2019-12-15 {
	description
	    "TNSR Release 19.12.";
    }

    revision 2019-08-30 {
	description
	    "TNSR Release 19.08.";
    }

    revision 2019-05-30 {
	description
	    "TNSR Release 19.05.";
    }

    revision 2019-02-15 {
	description
	    "TNSR Release 19.02.";
    }

    revision 2018-01-03 {
	description
	    "Initial revision.";
    }

    rpc dataplane-control {
	input {
	    leaf operation {
		type ngcom:service-operation;
		mandatory true;
		description
		    "The operation to perform";
	    }
	}
	output {
	    leaf stdout {
		type string;
	    }
	}
    }

    rpc dataplane-coredump {
	input {
	    leaf operation {
		type ngcom:service-op-enable-disable;
		mandatory true;
		description
		    "One of the strings 'enable' or 'disable'.";
	    }
	}
	output {
	    leaf stdout {
		type string;
	    }
	}
    }

    typedef uio-driver-t {
	type enumeration {
	    enum igb_uio {
		description
		    "UIO igb driver";
	    }
	    enum uio_pci_generic {
		description
		    "Generic UIO driver";
	    }
	    enum vfio-pci {
		description
		    "VFIO driver";
	    }
	}
    }

    typedef iova-mode-t {
	type enumeration {
	    enum pa {
		description
		    "IOVA as physical addresses mode";
	    }
	    enum va {
		description
		    "IOVA as virtual adresses mode";
	    }
	}
    }

    typedef device-type-t {
	type enumeration {
	    enum network {
		description
		    "Network interface";
	    }
	    enum crypto {
		description
		    "Cryptographic accelerator";
	    }
	    enum crypto-vf {
		description
		    "VF of cryptographic accelerator";
	    }
	}
    }

    typedef log-level-type-t {
	type enumeration {
	    enum emerg {
		description
		    "A panic conditions.";
	    }
	    enum alert {
		description
		    "Action must be taken immediately.";
	    }
	    enum crit {
		description
		    "Critical conditions.";
	    }
	    enum err {
		description
		    "Error conditions.";
	    }
	    enum warn {
		description
		    "Warning conditions.";
	    }
	    enum notice {
		description
		    "Normal but significant conitions.";
	    }
	    enum info {
		description
		    "Informational messages.";
	    }
	    enum debug {
		description
		    "Debug-level messages.";
	    }
	    enum disabled {
		description
		    "Logging will be disabled.";
	    }
	}
    }

    typedef dpdk-log-level-type-t {
	type enumeration {
	    enum emergency {
		description
		    "A panic conditions.";
	    }
	    enum alert {
		description
		    "Action must be taken immediately.";
	    }
	    enum critical {
		description
		    "Critical conditions.";
	    }
	    enum error {
		description
		    "Error conditions.";
	    }
	    enum warning {
		description
		    "Warning conditions.";
	    }
	    enum notice {
		description
		    "Normal but significant conitions.";
	    }
	    enum info {
		description
		    "Informational messages.";
	    }
	    enum debug {
		description
		    "Debug-level messages.";
	    }
	}
    }

    typedef blacklist-t {
	type union {
	    type string {
		pattern '[0-9a-fA-F]{1,4}:[0-9a-fA-F]{1,4}';
	    }
	    type string {
		pattern '[0-9a-fA-F]{1,4}:[0-9a-fA-F]{1,2}:[0-9a-fA-F]{1,2}[\.][0-9a-fA-F]';
	    }
	    type string {
		pattern '[0-9a-fA-F]{8}-[0-9a-fA-F]{4}-[0-9a-fA-F]{4}-[0-9a-fA-F]{4}-[0-9a-fA-F]{12}';
	    }
	}
    }

    container dataplane-config {
	description
	    "dataplane startup configurations";

	ngcliext:parent-fmt "dataplane";
	ngcliext:children-order "cpu unix ethernet buffers dpdk memory api-segment ip6 plugins statseg logging linux-cp";

	container cpu {
	    description
		"cpu stanza";

	    ngcliext:parent-fmt "$< $%";

	    must './main-core' {
		error-message "Main core must be specified when using worker " +
			      "threads";
	    }

	    leaf main-core {
		type uint16;
		description
		    "Assign main thread to a specific core.";
		must "not(../corelist-workers/corelist-worker[. = current()])" {
		     error-message "Cannot configure main-core same as " +
				   "corelist-worker.";
		}
		ngcliext:node-fmt "$< $% @@$n";
	    }

	    choice workers-type {
		description
		    "Number of workers or explicit list of worker thread core
		     bindings.";

		case workers {
		    leaf workers {
			type uint16;
			description
			    "Number of worker threads";
			ngcliext:node-fmt "$< $% @@$n";
		    }
		}
		case corelist-workers {
		    container corelist-workers {

			ngcliext:parent-fmt "$< $%";

			leaf-list corelist-worker {
			type uint16;
			description
			    "Place worker threads according to the
			    list of cores.";
			ngcliext:node-fmt "$< @@$n";
			}
		    }
		}
	    }

	    leaf skip-cores {
		type uint16 {
		    range "1..max";
		}
		description
		    "Sets number of CPU core(s) to be skipped.";
		ngcliext:node-fmt "$< $% @@$n";
	    }
	}

	container unix {
	    description
		"VPP unix section";

	    ngcliext:parent-fmt "$< $%";

	    leaf poll-sleep-usec {
		type uint32;
		units "microseconds";
		description
		    "Sleep time for main loop poll.";
		ngcliext:node-fmt "$< $% @@$n";
	    }
	}

	container ethernet {
	    description
		"Ethernet common configuration";

	    ngcliext:parent-fmt "$< $%";

	    leaf default-mtu {
		type uint32;
		default 1500;
		description
		    "Default ethernet MTU";
		ngcliext:node-fmt "$< $% @@$n";
	    }
	}

	container dpdk {
	    description
		"dpdk stanza";

	    ngcliext:parent-fmt "$< $%";

	    container blacklists {

		ngcliext:parent-fmt "$<";

		leaf-list blacklist {
		    type blacklist-t;
		    description
			"Blacklist devices by PCI vendor and device ID";
		    ngcliext:node-fmt "$< $% @@$n";
		}
	    }

	    list dev {
		key "id";
		unique "name";
		description
		    "Configs for a NIC or crypto device";

		ngcliext:parent-fmt "$< ${id} ${device-type}";

		leaf id {
		    type string;
		    description
			"The PCI ID for a device or 'default'.";
		    ngcliext:child-fmt "dev @@";
		}

		leaf device-type {
		    type device-type-t;
		    description
			"The type of the device.";
    		    ngcliext:child-fmt "@@";
		    ngcliext:node-op "test-set:%{name}%{devargs}%{num-rx-desc}%{num-tx-desc}%{num-rx-queues}%{num-tx-queues}%{tso}";
		    ngcliext:node-fmt "$<$n|";
		}

		leaf name {
		    type ngcom:if-identifier-31;
		    description
			"Given name for a dpdk device.";
		    must '../id != "default"' {
			error-message
			    "Setting a default network name is not supported";
		    }
		    ngcliext:node-fmt "$< $% @@$n";
		    ngcliext:sibling-fmt "@@";
		}

		container devargs {
		    description
			    "A list of name=value pairs provided
			     to a white-listed device.";

		    ngcliext:parent-fmt "$< $%";
		    ngcliext:sibling-fmt "devargs";

		    leaf-list arg {
			type string {
			     pattern "[^=]+=[^=]+";
			    length "1..128";
			}
			description
			    "A single name=value pair.";
			ngcliext:child-fmt "@@";
			ngcliext:node-fmt "$< @@$n";
		    }
		}

		leaf num-rx-desc {
		    type uint16;
		    description
			"Number of receive descriptors.";
		    ngcliext:node-fmt "$< $% @@$n";
		    ngcliext:sibling-fmt "@@";
		}

		leaf num-tx-desc {
		    type uint16;
		    description
			"Number of transmit descriptors.";
		    ngcliext:node-fmt "$< $% @@$n";
		    ngcliext:sibling-fmt "@@";
		}

		leaf num-rx-queues {
		    type uint16;
		    description
			"Number of receive queues.";
		    ngcliext:node-fmt "$< $% @@$n";
		    ngcliext:sibling-fmt "@@";
		}

		leaf num-tx-queues {
		    type uint16;
		    description
			"Number of transmit queues.";
		    ngcliext:node-fmt "$< $% @@$n";
		    ngcliext:sibling-fmt "@@";
		}

		leaf tso {
		    type string;
		    description
			"TCP segmentation offload. on/off";
		    ngcliext:node-fmt "$< $% @@$n";
		    ngcliext:sibling-fmt "@@";
		}
	    }

	    leaf dpdk-log-level {
		type dpdk-log-level-type-t;
		description
		    "DPDK log level";
		ngcliext:node-fmt "$< log-level @@$n";
	    }

	    leaf decimal-interface-names {
		type boolean;
		description
		    "Use decimal values of the PCI address instead of hexadecimal for devices";
		ngcliext:node-op "bool";
		ngcliext:node-fmt "|$< $%$n";
	    }

	    leaf tcp-udp-checksum {
		type boolean;
		description
		    "Enable hardware l4 checksums.";
		ngcliext:node-op "bool";
		ngcliext:node-fmt "|$< $%$n";
	    }

	    leaf no-multi-seg {
		type boolean;
		/*
		 * Interfaces without an MTU of their own use the ethernet
		 * default-mtu (1500 when not configured). It must leave room
		 * for the Ethernet header and two VLAN tags (22 bytes) in a
		 * buffer, as the interface MTU must in netgate-interface.
		 * The buffer data size is 2048 when not configured.
		 */
		must "current() = 'false' or "
		   + "(not(../../buffers/default-data-size) and "
		   + "(not(../../ethernet/default-mtu) or "
		   + "../../ethernet/default-mtu <= 2026)) or "
		   + "(not(../../ethernet/default-mtu) and "
		   + "../../buffers/default-data-size >= 1522) or "
		   + "../../ethernet/default-mtu <= "
		   + "../../buffers/default-data-size - 22" {
		    error-message
			"With dataplane dpdk no-multi-seg, the dataplane "
		      + "ethernet default-mtu must not exceed the dataplane "
		      + "buffers default-data-size minus 22 (2026 when "
		      + "default-data-size is not configured)";
		}
		/*
		 * LRO merges TCP segments into frames of up to 64 KB, which
		 * NIC drivers deliver as chains of buffers.
		 */
		must "current() = 'false' or not(../lro = 'true')" {
		    error-message
			"dataplane dpdk lro needs multi-segment buffers and "
		      + "can't be combined with dataplane dpdk no-multi-seg";
		}
		description
		    "Disable mutli-segment buffers.";
		ngcliext:node-op "bool";
		ngcliext:node-fmt "|$< $%$n";
	    }

	    leaf no-tx-checksum-offload {
		type boolean;
		description
		    "Disable transmit checksum offload.";
		ngcliext:node-op "bool";
		ngcliext:node-fmt "|$< $%$n";
	    }

	    leaf outer-checksum-offload {
		type boolean;
		description
		    "Enable hardware checksum offload for tunnel packets.";
		ngcliext:node-op "bool";
		ngcliext:node-fmt "|$< $%$n";
	    }

	    leaf lro {
		type boolean;
		description
		    "Enable large receive offload.";
		ngcliext:node-op "bool";
		ngcliext:node-fmt "|$< $%$n";
	    }

	    leaf no-pci {
		type boolean;
		description
		    "Disable PCI bus.";
		ngcliext:node-op "bool";
		ngcliext:node-fmt "|$< $%$n";
	    }

	    leaf uio-driver {
		type uio-driver-t;
		default vfio-pci;
		description
		    "Name of the uio driver";
		ngcliext:node-fmt "$< $% @@$n";
	    }

	    leaf iova-mode {
		type iova-mode-t;
		description
		    "IO virtual addresses mode";
		ngcliext:node-fmt "$< $% @@$n";
	    }

	    leaf telemetry {
		type boolean;
		description
		    "On/off telemetry in DPDK.";
		ngcliext:node-op "bool";
		ngcliext:node-fmt "|$< $%$n";
	    }
	}

	container memory {
	    description
		"Main heap configuration";

	    ngcliext:parent-fmt "$< $%";

	    leaf main-heap-size {
		type ngcom:memory-size-string;
		description
		    "Size of main heap. Should be a number. "+
		    "Optionally followed by a specified of k, m, or g, "+
		    "to indicate kilo, mega, or giga bytes. ";
		ngcliext:node-fmt "$< $% @@$n";
	    }

	    leaf main-heap-page-size {
		type ngcom:memory-page-size;
		default "2m";
		description
		    "Size of page in main heap. Should be a number. "+
		    "Optionally followed by a specified of k, m, or g, "+
		    "to indicate kilo, mega, or giga bytes. ";
		ngcliext:node-fmt "$< $% @@$n";
	    }
	}

	container api-segment {
	    description
		"VPP API segment configuration";

	    ngcliext:parent-fmt "$< $%";

	    leaf api-size {
		type ngcom:memory-size-string;
		default "16M";
		description
		    "The API shared memory size in bytes. An optional
		     K, M, or G suffix is allowed.  Default is 16M.  The API
		     memory size must be smaller than the global-size.";
		ngcliext:node-fmt "$< $% @@$n";
	    }

	    leaf global-size {
		type ngcom:memory-size-string;
		default "64M";
		description
		    "The global memory size in bytes. An optional
		     K, M, or G suffix is allowed.  Default is 64M.  The
		     global memory size must be larger than the api-size.";
		ngcliext:node-fmt "$< $% @@$n";
	    }

	    leaf api-pvt-heap-size {
		type ngcom:memory-size-string;
		default "128K";
		description
		    "The API private heap size in bytes. An optional
		     K, M, or G suffix is allowed.  Default is 128K.";
		ngcliext:node-fmt "$< $% @@$n";
	    }

	    leaf global-pvt-heap-size {
		type ngcom:memory-size-string;
		default "128K";
		description
		    "The global private heap size in bytes. An optional
		     K, M, or G suffix is allowed.  Default is 128K.";
		ngcliext:node-fmt "$< $% @@$n";
	    }
	}

	container buffers {
	    description
		"VPP pre-allocated buffers configuration";

	    ngcliext:parent-fmt "$< $%";

	    leaf buffers-per-numa {
		type uint32 {
		    range "1..4294967295";
		}
		description
		    "Pre-allocated buffers count";
		default 32768;
		ngcliext:node-fmt "$< $% @@$n";
	    }

	    leaf default-data-size {
		type uint32 {
		    range "1..4294967295";
		}
		description
		    "Amount of memory allocated per-buffer";
		ngcliext:node-fmt "$< $% @@$n";
	    }
	}

	container ip6 {
	    description
		"IPv6 settings";

	    ngcliext:parent-fmt "$< $%";

	    leaf hash-buckets {
		type uint32;
		description
		    "Number of hash buckets for IPv6 lookup table.";
		ngcliext:node-fmt "$< $% @@$n";
	    }

	    leaf heap-size {
		type ngcom:memory-size-string;
		description
		    "Size of heap for IPv6 FIB. Should be a number. "+
		    "Optionally followed by a specified of k, m, or g, "+
		    "to indicate kilo, mega, or giga bytes. ";
		ngcliext:node-fmt "$< $% @@$n";
	    }
	}

	container plugins {
	    description
		"VPP plugins";

	    ngcliext:parent-fmt "$< $%";

	    leaf-list plugin {
	        description "List of additional VPP plugins.
			    Short plugin name matches name_plugin.so file";
		type string {
		    pattern '[0-9a-zA-Z._-]+';
		    length "1..63";
		}

		ngcliext:node-fmt "$< $% @@ enable$n";
	    }
	}

	container statseg {
	    description
		"Statistics segment settings";

	    ngcliext:parent-fmt "$< $%";

	    leaf socket-name {
		type string {
		    pattern '/[0-9a-zA-Z/\._-]+';
		}
		description
		    "Absolute filesystem path to stats segment unix socket";
		ngcliext:node-fmt "$< $% @@$n";
	    }

	    leaf heap-size {
		type ngcom:memory-size-string;
		default 96M;
		description
		    "Size of heap for stats segment. Should be a number. "+
		    "Optionally followed by a specified of k, m, or g, "+
		    "to indicate kilo, mega, or giga bytes. ";
		ngcliext:node-fmt "$< $% @@$n";
	    }

	    container per-node-counters {

		ngcliext:parent-fmt "$< $%";

		leaf enabled {
		    type boolean;
		    default false;
		    description
			"Whether to enable per-node counters in the stats
			 segment";
		    ngcliext:node-op "bool";
		    ngcliext:node-fmt "|$< enable$n";
		}
	    }
	}

	container logging {
	    description
		"Logging segment settings";

	    ngcliext:parent-fmt "$< $%";

	    leaf size {
		type int32 {
		    range "512..16777216";
		}
		description
		    "Number of log messages in fifo bufer.";
		ngcliext:node-fmt "$< $% @@$n";
	    }

	    leaf unthrottle-time {
		type int32 {
		    range "-1..max";
		}
		description
		    "Message unthrottling time (in seconds). ";
		ngcliext:node-fmt "$< $% @@$n";
	    }

	    leaf default-log-level {
		type log-level-type-t;
		description
		    "Default log level to process message into the "+
		    "internal message queue.";
		ngcliext:node-fmt "$< $% @@$n";
	    }

	    leaf default-syslog-log-level {
		type log-level-type-t;
		default notice;
		description
		    "Default log level to process messages into the syslog. "+
		    "Message will be preocessed to syslog if log level "+
		    "is less then or equal to the message's log level.";
		ngcliext:node-fmt "$< $% @@$n";
	    }
	}

	container linux-cp {
	    description
		"Linux-cp (host stack connectivity) settings";

	    ngcliext:parent-fmt "$< $%";

	    leaf nl-rx-buffer-size {
		type uint32;
		description
		    "Size of netlink socket receive buffer.";
		ngcliext:node-fmt "$< $% @@$n";
	    }

	    leaf nl-batch-size {
		type uint32;
		description
		    "Number of netlink messages to process at a time.";
		ngcliext:node-fmt "$< $% @@$n";
	    }

	    leaf nl-batch-delay-ms {
		type uint32;
		description
		    "Delay in ms between processing batches of netlink
		     messages.";
		ngcliext:node-fmt "$< $% @@$n";
	    }

	    leaf num-rx-queues {
		type uint16 {
		    range "1..256";
		}
		default "1";
		description
		    "Number of receive queues created on linux-cp tap and
		     tun interfaces.";
		ngcliext:node-fmt "$< $% @@$n";
	    }

	    leaf num-tx-queues {
		type uint16 {
		    range "1..256";
		}
		description
		    "Number of transmit queues created on linux-cp tap and
		     tun interfaces.";
		ngcliext:node-fmt "$< $% @@$n";
	    }
	}
    }

    container dataplane-state {
	config "false";

	description
	    "dataplane state";

	leaf config-synced {
	    type boolean;
	    description
		"True when the running configuration has been fully
		 applied to the running VPP instance.  False or absent
		 while VPP is down or starting, or while a configuration
		 replay is pending after a VPP start or restart.";
	}

	container cpu {
	    description
		"cpu stanza";

	    container threads {
		description
		    "Threads.";

		list thread {
		    key "id";
		    description
			"Thread data.";

		    leaf id {
			type uint32;
			description
			    "Thread index.";
		    }

		    leaf name {
			type ngcom:identifier-64;
			description
			    "Thread name (i.e. vpp_main or vpp_wk_0).";
		    }

		    leaf type {
			type string {
			    length "0..64";
			}
			description
			    "Thread type (i.e. workers or stats).";
		    }

		    leaf pid {
			type uint32;
			description
			    "Thread process id.";
		    }

		    leaf cpu-id {
			type uint32;
			description
			    "Thread pinned to cpu (logical cores).";
		    }

		    leaf core {
			type uint32;
			description
			    "Thread pinned to actual physical core.";
		    }

		    leaf cpu-socket {
			type uint32;
			description
			    "Thread is running on which cpu socket.";
		    }
		}
	    }
	}
    }
}
