module netgate-ssh-server {

    yang-version 1.1;

    namespace "urn:netgate:xml:yang:netgate-ssh-server";
    prefix "ngsshs";

    import netgate-cli-extensions {
	prefix "ngcliext";
    }

    import netgate-common {
	prefix "ngcom";
    }

    organization "Netgate";

    contact "Web: <http://www.netgate.com>";

    description
	"This YANG module provides a data model for the SSH server.

	 Copyright 2020, 2021, 2025 Rubicon Communications, LLC.";

    revision 2025-02-01 {
	description
	    "TNSR Release 25.02.";
    }

    revision 2021-02-15 {
	description
	    "TNSR Release 21.02.";
    }

    revision 2020-06-15 {
	description
	    "TNSR Release 20.06.";
    }

    revision 2020-04-08 {
	description
	    "Initial release.";
    }

    rpc ssh-server-control {
	description
	    "Control of SSH server for dataplane interfaces.";

        input {
	    leaf operation {
	        type ngcom:service-operation;
	        mandatory true;
	        description
                    "One of the strings 'start', 'stop', 'restart',
                     or 'status'.";
	    }

	    leaf namespace {
		type ngcom:network-namespace;
		description
		    "Network namespace.";
	    }
        }

        output {
	    leaf stdout {
	        type string;
	        description
                    "Command output.";
            }
        }
    }

    container ssh-server-config {
        description
            "Configuration for the SSH server.";

	ngcliext:parent-fmt "ssh";

	container dataplane {
	    description
		"Dataplane-specific parameters of SSH server.";

	    ngcliext:parent-fmt "$< dataplane";

	    leaf enable {
		type boolean;
		description
		    "If true, SSH server is enabled for dataplane
		    interfaces.";
		ngcliext:node-op "bool";
		ngcliext:node-fmt "|$< enable$n";
	    }

	    container netconf-subsystem {
		description
		    "Dataplane netconf subsystem settings.";

		ngcliext:parent-fmt "$< $%";

		leaf enable {
		    type boolean;
		    description
			"If true, netconf subsystem is enabled for " +
			"dataplane SSH server.";
		    must "current() = 'false' or ../../enable = 'true'" {
			error-message "Dataplane SSH server must be enabled " +
				      "in order to enable dataplane SSH "+
				      "netconf-subsystem.";
		    }
		    ngcliext:node-op "bool";
		    ngcliext:node-fmt "|$< enable %{port}$n";
		}

		leaf port {
		    type uint16;
		    description
			"TCP port for dataplane SSH server netconf subsystem.";
		    default 830;
		    ngcliext:sibling-fmt "port @@";
		}
	    }
	}

	container host {
	    description
		"Host-specific parameters of SSH server.";

	    ngcliext:parent-fmt "$< $%";

	    container netconf-subsystem {
		description
		    "Host netconf subsystem settings.";

		ngcliext:parent-fmt "$< $%";

		leaf enable {
		    type boolean;
		    description
			"If true, netconf subsystem is enabled for " +
			"host SSH server.";
		    ngcliext:node-op "bool";
		    ngcliext:node-fmt "|$< enable %{port}$n";
		}

		leaf port {
		    type uint16;
		    description
			"TCP port for host SSH server netconf subsystem.";
		    default 830;
		    ngcliext:sibling-fmt "port @@";
		}
	    }
	}
    }
}
