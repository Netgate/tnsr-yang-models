module netgate-restconf-cli {

    yang-version 1.1;

    namespace "urn:netgate:xml:yang:netgate-restconf-cli";
    prefix "ngrccli";

    import clixon-restconf {
	prefix clrc;
    }

    import netgate-cli-extensions {
	prefix "ngcliext";
    }

    organization "Netgate";

    contact "Web: <http://www.netgate.com>";

    description
	"This YANG module provides TNSR CLI augments for
	 clixon RESTCONF model.

	 Copyright 2021, 2023, 2024 Rubicon Communications, LLC.";

    revision 2025-02-01 {
	description
	    "TNSR Release 25.02.";
    }

    revision 2023-02-15 {
	description
	    "TNSR Release 23.02.";
    }

    revision 2021-06-15 {
	description
	    "TNSR Release 21.07.";
    }

    revision 2021-03-29 {
	description
	    "initial release.";
    }

    augment "/clrc:restconf" {
	ngcliext:node-fmt "${enable-core-dump}restconf$n";
	ngcliext:pre-children-op "push";
    }

    augment "/clrc:restconf/clrc:enable-core-dump" {
	ngcliext:child-op "bool";
	ngcliext:child-fmt "|service restconf coredump enable$n";
    }

    augment "/clrc:restconf/clrc:enable" {
	ngcliext:node-fmt "^$% @@$n";
    }

    augment "/clrc:restconf/clrc:enable-http-data" {
	ngcliext:node-op "bool";
	ngcliext:node-fmt "|^gui enable$n";
    }

    augment "/clrc:restconf/clrc:auth-type" {
	ngcliext:node-fmt "^global authentication-type @@$n";
    }

    augment "/clrc:restconf/clrc:server-ca-cert-path" {
	ngcliext:node-fmt "^global server-ca-cert-path @@$n";
    }

    augment "/clrc:restconf/clrc:server-cert-path" {
	ngcliext:node-fmt "^global server-certificate @@$n";
    }

    augment "/clrc:restconf/clrc:server-key-path" {
	ngcliext:node-fmt "^global server-key @@$n";
    }

    augment "/clrc:restconf/clrc:socket/clrc:namespace" {
	ngcliext:node-fmt "^server @@%{address}%{port}%{ssl}$n";
    }

    augment "/clrc:restconf/clrc:socket/clrc:address" {
	ngcliext:sibling-fmt " @@";
    }

    augment "/clrc:restconf/clrc:socket/clrc:port" {
	ngcliext:sibling-fmt " @@";
    }

    augment "/clrc:restconf/clrc:socket/clrc:ssl" {
	ngcliext:sibling-fmt " @@";
    }
}
