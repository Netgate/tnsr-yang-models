module netgate-kea {

    yang-version 1.1;

    namespace "urn:netgate:xml:yang:netgate-kea";
    prefix "ngkea";

    import clixon-lib {
	prefix "cl";
    }

    import ietf-inet-types {
	prefix "inet";
    }

    import ietf-yang-types {
	prefix "yang";
    }

    import netgate-cli-extensions {
	prefix "ngcliext";
    }

    import netgate-common {
	prefix "ngcom";
    }

    organization "Netgate";

    contact "Web: <http://www.netgate.com>";

    description
	"This YANG module provides a data model for the Kea DHCP server.

	 Copyright 2019-2025 Rubicon Communications, LLC.";

    revision 2026-10-01 {
	description
	    "TNSR Release 26.10.";
    }

    revision 2025-02-01 {
	description
	    "TNSR Release 25.02.";
    }

    revision 2024-10-01 {
	description
	    "TNSR Release 24.10.";
    }

    revision 2023-11-01 {
	description
	    "TNSR Release 23.11.";
    }

    revision 2023-02-15 {
	description
	    "TNSR Release 23.02.";
    }

    revision 2022-06-15 {
	description
	    "TNSR Release 22.06.";
    }

    revision 2022-02-15 {
	description
	    "TNSR Release 22.02.";
    }

    revision 2021-11-15 {
	description
	    "TNSR Release 21.11.";
    }

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-12-15 {
	description
	    "TNSR Release 19.12.";
    }

    revision 2019-08-30 {
	description
	    "TNSR Release 19.08.";
    }

    revision 2019-05-30 {
	description
	    "TNSR Release 19.05.";
    }

    revision 2019-02-15 {
	description
	    "TNSR Release 19.02.";
    }

    typedef duid {
	type string {
	    pattern '(([0-9a-fA-F]{2}){2,128})';
	}
	description
	    "DHCP Unique Identifier (RFC-3315).";
    }

    typedef kea-host-id-method {
	type enumeration {
	    enum hw-address {
		description
		    "The host's identifying MAC address.";
	    }
	    enum duid {
		description
		    "The host's identifying DUID.";
	    }
	    enum circuit-id {
		description
		    "The host's identifying circuit-id address.";
	    }
	    enum client-id {
		description
		    "The host's identifying client-id address.";
	    }
	}
    }

    typedef kea-dhcp4-option-def-id {
	type string {
	    length "1..63";
	    pattern '[a-zA-Z][a-zA-Z0-9_-]*';
	}
    }

    typedef kea-dhcp4-option-def-type {
	type enumeration {
	    enum binary {
		description
		    "An arbitrary string of bytes, specified
		     as a set of hexadecimal digits.";
	    }

	    enum boolean {
		description
		    "A boolean value.";
	    }

	    enum empty {
		description
		    "No value; data is carried in sub-options.";
	    }

	    enum fqdn {
		description
		    "Fully qualified domain name.";
	    }

	    enum ipv4-address {
		description
		    "Dotted quad IP address.";
	    }

	    enum ipv6-address {
		description
		    "An IPv6 address in colon notation.";
	    }

	    enum ipv6-prefix {
		description
		    "An IPv6 address and prefix length.";
	    }

	    enum psid {
		description
			"PSID and PSID length separated by a slash,
			 e.g. 3/4 specifies PSID=3 and PSID length=4.
			 In the wire format it is represented by an
			 8-bit field carrying PSID length (in this
			 case equal to 4) and the 16-bits-long PSID
			 value field (in this case equal to
			 '0011000000000000b' using binary notation).
			 Allowed values for a PSID length are 0 to
			 16. See RFC 7597 for details about the PSID
			 wire representation.";
	    }

	    enum record {
		description
		    "Structured data that may be comprised of any
		     types (except 'record' and 'empty'). The array
		     flag applies to the last field only.";
	    }

	    enum string {
		description
		    "Any text.";
	    }

	    enum tuple {
		description
		    "A length encoded as an 8-bit unsigned integer
		     followed by a string of this length.";
	    }

	    enum uint8 {
		description
		    "8-bit unsigned integer with allowed values 0 to 255.";
	    }

	    enum uint16 {
		description
		    "16-bit unsigned integer with allowed values 0 to 65535.";
	    }

	    enum uint32 {
		description
		    "32-bit unsigned integer with allowed values 0
		     to 4294967295.";
	    }

	    enum int8 {
		description
		    "8-bit signed integer with allowed values -128 to 127.";
	    }

	    enum int16 {
		description
		    "16-bit signed integer with allowed values -32768
		     to 32767.";
	    }

	    enum int32 {
		description
		    "32-bit signed integer with allowed values -2147483648
		     to 2147483647.";
	    }
	}
    }

    typedef kea-dhcp4-option-standard {
	type enumeration {

	    enum time-offset {
		description
		    "time-offset";
	    }

	    enum routers {
		description
		    "routers";
	    }

	    enum time-servers {
		description
		    "time-servers";
	    }

	    enum name-servers {
		description
		    "name-servers";
	    }

	    enum domain-name-servers {
		description
		    "domain-name-servers";
	    }

	    enum log-servers {
		description
		    "log-servers";
	    }

	    enum cookie-servers {
		description
		    "cookie-servers";
	    }

	    enum lpr-servers {
		description
		    "lpr-servers";
	    }

	    enum impress-servers {
		description
		    "impress-servers";
	    }

	    enum resource-location-servers {
		description
		    "resource-location-servers";
	    }

	    enum boot-size {
		description
		    "boot-size";
	    }

	    enum merit-dump {
		description
		    "merit-dump";
	    }

	    enum domain-name {
		description
		    "domain-name";
	    }

	    enum swap-server {
		description
		    "swap-server";
	    }

	    enum root-path {
		description
		    "root-path";
	    }

	    enum extensions-path {
		description
		    "extensions-path";
	    }

	    enum ip-forwarding {
		description
		    "ip-forwarding";
	    }

	    enum non-local-source-routing {
		description
		    "non-local-source-routing";
	    }

	    enum policy-filter {
		description
		    "pllicy-filter";
	    }

	    enum max-dgram-reassembly {
		description
		    "max-dgram-reassembly";
	    }

	    enum default-ip-ttl {
		description
		    "default-ip-ttl";
	    }

	    enum path-mtu-aging-timeout {
		description
		    "path-mtu-aging-timeout";
	    }

	    enum path-mtu-plateau-table {
		description
		    "path-mtu-plateau-table";
	    }

	    enum interface-mtu {
		description
		    "interface-mtu";
	    }

	    enum all-subnets-local {
		description
		    "all-subnets-local";
	    }

	    enum broadcast-address {
		description
		    "broadcast-address";
	    }

	    enum perform-mask-discovery {
		description
		    "perform-mask-discovery";
	    }

	    enum mask-supplier {
		description
		    "mask-supplier";
	    }

	    enum router-discovery {
		description
		    "router-discovery";
	    }

	    enum router-solicitation-address {
		description
		    "router-solicitation-address";
	    }

	    enum static-routes {
		description
		    "static-routes";
	    }

	    enum trailer-encapsulation {
		description
		    "trailer-encapsulation";
	    }

	    enum arp-cache-timeout {
		description
		    "arp-cache-timeout";
	    }

	    enum ieee802-3-encapsulation {
		description
		    "ieee802-3-encapsulation";
	    }

	    enum default-tcp-ttl {
		description
		    "default-tcp-ttl";
	    }

	    enum tcp-keepalive-interval {
		description
		    "tcp-keepalive-interval";
	    }

	    enum tcp-keepalive-garbage {
		description
		    "tcp-keepalive-garbage";
	    }

	    enum nis-domain {
		description
		    "nis-domain";
	    }

	    enum nis-servers {
		description
		    "nis-servers";
	    }

	    enum ntp-servers {
		description
		    "ntp-servers";
	    }

	    enum vendor-encapsulated-options {
		description
		    "vendor-encapsulated-options";
	    }

	    enum netbios-name-servers {
		description
		    "netbios-name-servers";
	    }

	    enum netbios-dd-server {
		description
		    "netbios-dd-server";
	    }

	    enum netbios-node-type {
		description
		    "netbios-node-type";
	    }

	    enum netbios-scope {
	        description
		    "netbios-scope";
	    }

	    enum font-servers {
		description
		    "font-servers";
	    }

	    enum x-display-manager {
		description
		    "x-display-manager";
	    }

	    enum dhcp-option-overload {
		description
		    "dhcp-option-overload";
	    }

	    enum dhcp-server-identifier {
		description
		    "dhcp-server-identifier";
	    }

	    enum dhcp-message {
		description
		    "dhcp-message";
	    }

	    enum dhcp-max-message-size {
		description
		    "dhcp-max-message-size";
	    }

	    enum vendor-class-identifier {
		description
		    "vendor-class-identifier";
	    }

	    enum nwip-domain-name {
		description
		    "nwip-domain-name";
	    }

	    enum nwip-suboptions {
		description
		    "nwip-suboptions";
	    }

	    enum nisplus-domain-name {
		description
		    "nisplus-domain-name";
	    }

	    enum nisplus-servers {
		description
		    "nisplus-servers";
	    }

	    enum tftp-server-name {
		description
		    "tftp-server-name";
	    }

	    enum boot-file-name {
		description
		    "boot-file-name";
	    }

	    enum mobile-ip-home-agent {
		description
		    "mobile-ip-home-agent";
	    }

	    enum smtp-server {
		description
		    "smtp-server";
	    }

	    enum pop-server {
		description
		    "pop-server";
	    }

	    enum nntp-server {
		description
		    "nntp-server";
	    }

	    enum www-server {
		description
		    "www-server";
	    }

	    enum finger-server {
		description
		    "finger-server";
	    }

	    enum irc-server {
		description
		    "irc-server";
	    }

	    enum streettalk-server {
		description
		    "streettalk-server";
	    }

	    enum streettalk-directory-assistance-server {
		description
		    "streettalk-directory-assistance-server";
	    }

	    enum user-class {
		description
		    "user-class";
	    }

	    enum slp-directory-agent {
		description
		    "slp-directory-agent";
	    }

	    enum slp-service-scope {
		description
		    "slp-service-scope";
	    }

	    enum nds-servers {
		description
		    "nds-servers";
	    }

	    enum nds-tree-name {
		description
		    "nds-tree-name";
	    }

	    enum nds-context {
		description
		    "nds-context";
	    }

	    enum bcms-controller-names {
		description
		    "bcms-controller-names";
	    }

	    enum bcms-controller-address {
		description
		    "bcms-controller-address";
	    }

	    enum client-system {
		description
		    "client-system";
	    }

	    enum client-ndi {
		description
		    "client-ndi";
	    }

	    enum uuid-guid {
		description
		    "uuid-guid";
	    }

	    enum uap-servers {
		description
		    "uap-servers";
	    }

	    enum geoconf-civic {
		description
		    "geoconf-civic";
	    }

	    enum pcode {
		description
		    "pcode";
	    }

	    enum tcode {
		description
		    "tcode";
	    }

	    enum v6-only-preferred {
		description
		    "v6-only-preferred";
	    }

	    enum netinfo-server-address {
		description
		    "netinfo-server-address";
	    }

	    enum netinfo-server-tag {
		description
		    "netinfo-server-tag";
	    }

	    enum v4-captive-portal {
		description
		    "v4-captive-portal replaces default-url";
	    }

	    enum auto-config {
		description
		    "auto-config";
	    }

	    enum name-service-search {
		description
		    "name-service-search";
	    }

	    enum domain-search {
		description
		    "domain-search";
	    }

	    enum classless-static-route {
		description
		    "classless-static-route";
	    }

	    enum vivco-suboptions {
		description
		    "vivco-suboptions";
	    }

	    enum vivso-suboptions {
		description
		    "vivso-suboptions";
	    }

	    enum pana-agent {
		description
		    "pana-agent";
	    }

	    enum v4-lost {
		description
		    "v4-lost";
	    }

	    enum capwap-ac-v4 {
		description
		    "capwap-ac-v4";
	    }

	    enum sip-ua-cs-domains {
		description
		    "sip-ua-cs-domains";
	    }

	    enum v4-sztp-redirect {
		description
		    "v4-sztp-redirect";
	    }

	    enum rdnss-selection {
		description
		    "rdnss-selection";
	    }

	    enum v4-portparams {
		description
		    "v4-portparams";
	    }

	    enum v4-dnr {
		description
		    "v4-dnr";
	    }

	    enum option-6rd {
		description
		    "option-6rd";
	    }

	    enum v4-access-domain {
		description
		    "v4-access-domain";
	    }
	}
    }

    typedef kea-dhcp4-option {
	type union {
	    type kea-dhcp4-option-standard;

	    type leafref {
		path "/ngkea:kea-config/dhcp4-server/ngkea:Dhcp4"
		    + "/ngkea:option-def/ngkea:name";
	    }
	}
    }

    typedef kea-logger-name {
	type enumeration {
	    enum kea-dhcp4 {
		description
		    "DHCPv4 server default logging";
	    }

	    enum kea-dhcp4.alloc-engine {
		description
		    "DHCPv4 lease allocation";
	    }

	    enum kea-dhcp4.bad-packets {
		description
		    "DHCPv4 packets that are dropped or rejected";
	    }

	    enum kea-dhcp4.callouts {
		description
		    "DHCPv4 hook point callout registration/execution";
	    }

	    enum kea-dhcp4.commands {
		description
		    "DHCPv4 commands received over the command channel";
	    }

	    enum kea-dhcp4.ddns {
		description
		    "DHCPv4 client FQDN and Hostname option processing";
	    }

	    enum kea-dhcp4.dhcp4 {
		description
		    "DHCPv4 server basic operations";
	    }

	    enum kea-dhcp4.dhcpsrv {
		description
		    "DHCPv4 libkea-dhcpsrv library default logging";
	    }

	    enum kea-dhcp4.eval {
		description
		    "DHCPv4 client classification expression evaluation";
	    }

	    enum kea-dhcp4.hooks {
		description
		    "DHCPv4 hook registration/deregistration";
	    }

	    enum kea-dhcp4.hosts {
		description
		    "DHCPv4 host reservation management";
	    }

	    enum kea-dhcp4.leases {
		description
		    "DHCPv4 lease allocation";
	    }

	    enum kea-dhcp4.options {
		description
		    "DHCPv4 option processing/parsing/encoding";
	    }

	    enum kea-dhcp4.packets {
		description
		    "DHCPv4 packet reception/transmission";
	    }

	    enum kea-dhcp4.stat-cmds-hooks {
		description
		    "DHCPv4 libdhcp_stat_cmds library default logging";
	    }
	}
    }

    typedef kea-logger-severity {
	type enumeration {
	    enum fatal {
		description
		    "Associated with messages generated by a condition
		     that is so serious that the server cannot
		     continue executing.";
	    }

	    enum error {
		description
		    "Associated with messages generated by an error
		     condition. The server will continue executing,
		     but the results may not be as expected.";
	    }

	    enum warn {
		description
		    "Indicates an out of the ordinary condition.
		     However, the server will continue executing
		     normally.";
	    }

	    enum info {
		description
		    "An informational message marking some event.";
	    }

	    enum debug {
		description
		    "Messages produced for debugging purposes.";
	    }
	}
    }

    typedef kea-output-keyword {
	type string {
	    pattern "stdout|stderr|syslog(:[a-zA-Z0-9]+){0,1}";
	}
	description
	    "The special output locations stdout, stderr, or syslog
	     with an optional facility name.";
    }

    typedef kea-output-filename {
	type string {
	    length "1..max";
	    pattern '[^\*].*';
	}
	description
	    "A filename.";
    }

    typedef kea-output-location {
	type union {
	    type kea-output-keyword;
	    type kea-output-filename;
	}
    }
    
    typedef ipv4-range {
	type string {
	    pattern
		  '(([0-9]|[1-9][0-9]|1[0-9][0-9]|2[0-4][0-9]|25[0-5])\.){3}'
		+ '([0-9]|[1-9][0-9]|1[0-9][0-9]|2[0-4][0-9]|25[0-5])'
		+ '(-'
		+ '(([0-9]|[1-9][0-9]|1[0-9][0-9]|2[0-4][0-9]|25[0-5])\.){3}'
		+ '([0-9]|[1-9][0-9]|1[0-9][0-9]|2[0-4][0-9]|25[0-5])'
		+ ')';
	    }
    }

    typedef ipv4-prefix-or-range {
	type union {
	    type inet:ipv4-prefix;
	    type ipv4-range;
	}
    }

    typedef kea-operation {
	type enumeration {
	    enum start {
		description
		    "Start daemon";
	    }
	    enum stop {
		description
		    "Stop daemon";
	    }
	    enum reload {
		description
		    "Reload config file";
	    }
	    enum status {
		description
		    "Daemon status";
	    }
	}
    }

    typedef kea-service-name {
	type enumeration {
	    enum dhcp4 {
		description
		    "DHCP4 service";
	    }
	}
    }

    rpc kea-control {
	input {
	    leaf operation {
		type kea-operation;
		mandatory true;
		description
		    "One of the strings 'start', 'stop', 'reload',
		     or 'status'.";
	    }
	    leaf kea-service {
		type kea-service-name;
	    }
	}
	output {
	    leaf stdout {
		type string;
	    }
	}
    }

    rpc kea-coredump {
	input {
	    leaf operation {
		type ngcom:service-op-enable-disable;
		mandatory true;
		description
		    "One of the strings 'enable', or 'disable'.";
	    }
	}
	output {
	    leaf stdout {
		type string;
	    }
	}
    }

    typedef kea-show-request {
	type enumeration {
	    enum config {
		description
		    "Get on-disk configuration files.";
	    }
	}
    }

    typedef kea-show-parameter {
	type enumeration {
	    enum dhcp4 {
		description
		    "DHCP IPv4 configuration file.";
	    }
	    enum keactrl {
		description
		    "DHCP Kea control configuration file.";
	    }
	}
    }

    typedef kea-lease-state {
	type enumeration {
	    enum default {
		value 0;
		description
		    "Default lease state.";
	    }
	    enum declined {
		value 1;
		description
		    "Declined lease.";
	    }
	    enum expired {
		value 2;
		description
		    "Expired and reclaimed lease.";
	    }
	    enum unknown {
		description
		    "Unknown state.";
	    }
	}
	description
	    "Lease state values.";
    }

    rpc kea-show {
	input {
	    leaf request {
		type kea-show-request;
		mandatory true;
		description
		    "A Kea show request type.  The string 'config'
		     along with parameter 'dhcp4'.
		     This request will return the contents of the
		     corresponding on-disk Kea configuration file.";
	    }
	    leaf param {
		type kea-show-parameter;
		mandatory true;
		description
		    "Only the string 'dhcp4' is supported.";
	    }
	}
	output {
	    leaf stdout {
		type string;
	    }
	}
    }

    grouping kea-dhcp4-option-def-group {
	description
	    "Kea DHCPv4 custom option definition information.";

	list option-def {
	    key name;
	    description
		"List of DHCPv4 custom option definition.";

	    ngcliext:node-fmt "^$% @{name}$n";
	    ngcliext:pre-children-op "push";

	    leaf name {
		type kea-dhcp4-option-def-id;
		description
		    "The server requires an option name to identify an
		     option definition.";
	    }

	    leaf array {
		type boolean;
		description
		    "If true, specifies an array of values.  If false,
		     specifies a singular datum or record.";
		ngcliext:node-fmt "^$% @@$n";
	    }

	    leaf code {
		type uint8;
		mandatory true;
		description
		    "The numeric uint8 option code.";
		ngcliext:node-fmt "^$% @@$n";
	    }

	    leaf encapsulate {
		type ngcom:description-63;
		description
		    "The name of the option space being encapsulated
		     by the particular option.";
		ngcliext:node-fmt "^$% @@$n";
	    }

	    leaf record-types {
		type ngcom:description-63;
		description
		    "A comma separated list of record field types.";
		ngcliext:node-fmt "^$% @@$n";
	    }

	    leaf space {
		type ngcom:description-63;
		description
		    "The namespace for the option definition.";
		ngcliext:node-fmt "^$% @@$n";
	    }

	    leaf type {
		type kea-dhcp4-option-def-type;
		mandatory true;
		description
		    "The data-type of the option's value.";
		ngcliext:node-fmt "^$% @@$n";
	    }
	}
    }

    grouping kea-dhcp4-option-group {
	description
	    "Kea DHCPv4 option information.";

	list option-data {
	    key name;
	    description
		"List of DHCPv4 options and values.";

	    ngcliext:node-fmt "^option @{name}$n";
	    ngcliext:pre-children-op "push";

	    leaf name {
		type kea-dhcp4-option;
		description
		    "The server requires an option name to identify an
		     option.";
	    }

	    leaf always-send {
		type boolean;
		description
		    "To enforce the addition of a particular option
		     set the always-send flag to true.";
		ngcliext:node-fmt "^$% @@$n";
	    }

	    leaf csv-format {
		type boolean;
		description
		    "If this value is not specified the server will
		     assume that the option data is specified as a
		     list of comma separated values to be assigned to
		     individual fields of the DHCP option.";
		ngcliext:node-fmt "^$% @@$n";
	    }

	    leaf data {
		type string;
		description
		    "If the option data is unspecified it defaults to
		     an empty value. The empty value is mostly used
		     for the options which have no payload (boolean
		     options), but it is legal to specify empty values
		     for some options which carry variable length data
		     and which the specification allows for the length
		     of 0. For such options, the data parameter may be
		     omitted in the configuration.";
		ngcliext:node-fmt "^$% @@$n";
	    }

	    leaf space {
		type string;
		description
		    "If the option space is unspecified it will
		     default to 'dhcp4' which is an option space
		     holding DHCPv4 standard options";
		ngcliext:node-fmt "^$% @@$n";
	    }
	}
    }

    grouping kea-logging-group {
	description
	    "Kea logging information.";

	list loggers {
	    key name;
	    description
		"List of logging facilities and parameters.";

	    ngcliext:node-fmt "^logging @{name}$n";
	    ngcliext:pre-children-op "push";

	    leaf name {
		type kea-logger-name;
		description
		    "The name of a Kea logger.";
	    }

	    list output_options {
		key output;
		description
		    "List of output options for a logger.";

		ngcliext:node-fmt "^output @{output}$n";
		ngcliext:pre-children-op "push";

		leaf output {
		    type kea-output-location;
		    description
			"The logger's file or keyword output location.";
		}

		leaf maxver {
		    type uint32 {
			range "1..max";
		    }
		    description
			"The maximum number of rotation log files
			 to keep. The default value is 1.";
		    ngcliext:node-fmt "^$% @@$n";
		}

		leaf maxsize {
		    type uint32 {
			range "204800..max";
		    }
		    description
			"The maximum size of a rotating log file in bytes.
			 The default is 10MB.";
		    ngcliext:node-fmt "^$% @@$n";
		}

		leaf flush {
		    type boolean;
		    description
			"If true, each log message is flushed as it is
			 logged at a slight performance penalty.";
		    ngcliext:node-fmt "^$% @@$n";
		}
	    }

	    leaf severity {
		type kea-logger-severity;
		mandatory true;
		description
		    "A Kea logger severity level.";
		ngcliext:node-fmt "^$% @@$n";
	    }

	    leaf debuglevel {
		type uint16 {
		    range "0..99";
		}
		description
		    "A Kea debug level.";
		ngcliext:node-fmt "^debug-level @@$n";
	    }
	}
    }

    container kea-config {

	description
	    "Dynamic Host Configuration Protocol (DHCP) configuration.";

	container keactrl {
	    description
		"This section contains parameters for the keactrl
		 configuration file.";

	    container dhcp4 {
		description
		    "Parameters for the DHCP IPv4 server.";

		ngcliext:parent-fmt "dhcp4";

		leaf enable {
		    type boolean;
		    description
			"If true, the Kea dhcp4 server is enabled.";
		    ngcliext:node-op "bool";
		    ngcliext:node-fmt "|$< enable$n";
		}
	    }
	}

	container dhcp4-server {
	    description
		"Gather all the parts that contribute to the DHCP4 server.";

	    ngcliext:node-fmt "dhcp4 server$n";
	    ngcliext:pre-children-op "push";

	    container Dhcp4 {
		description
		    "Configuration for the Kea DHCP IPv4 Server";

		leaf authoritative {
		    type boolean;
		    default true;
		    description
			"Global flag to determine whether to send a NAK in
			 response to requests by clients for unknown IP
			 addresses. Defaults to true.";
		    ngcliext:node-fmt "^$% @@$n";
		}

		uses kea-dhcp4-option-def-group;

		uses kea-dhcp4-option-group;

		uses kea-logging-group;

		leaf decline-probation-period {
		    type uint32;
		    description
			"The decline-probation-period specifies the period
			 in seconds in which the server will recycle
			 declined leases.  The default period is 86400
			 seconds (24 hours).";
		    ngcliext:node-fmt "^$% @@$n";
		}

		leaf description {
		    type ngcom:description-63;
		    description
			"A user-supplied description of the server.";
		    ngcliext:node-fmt "^$% @@$n";
		    cl:ignore-compare;
		}

		leaf echo-client-id {
		    type boolean;
		    description
			"The echo-client-id boolean value specifies that
			 the server should or should-not reply with the
			 client-id if the client sent it.  Setting this to
			 false enables RFC-2131 backward compatibitlity.";
		    ngcliext:node-fmt "^$% @@$n";
		}

		leaf match-client-id {
		    type boolean;
		    description
			"If match-client-id is false, the DHCP server will
			 match clients using the 'chaddr' field.";
		    ngcliext:node-fmt "^$% @@$n";
		}

		leaf next-server {
		    type inet:ipv4-address;
		    description
			"This next-server IPv4 address is used as the
			siaddr field.";
		    ngcliext:node-fmt "^$% @@$n";
		}

		leaf rebind-timer {
		    type uint32;
		    description
			"The RFC-2131 T2 rebind value in seconds.";
		    ngcliext:node-fmt "^$% @@$n";
		}

		leaf renew-timer {
		    type uint32;
		    description
			"The RFC-2131 T1 renewal value in seconds.";
		    ngcliext:node-fmt "^$% @@$n";
		}

		leaf valid-lifetime {
		    type uint32;
		    description
			"The valid duration for an assigned lease in
			seconds.";
		    ngcliext:node-fmt "^$% @@$n";
		}

		container expired-leases-processing {
			leaf reclaim-timer-wait-time {
				type uint16;
				default 10;
				description
				"This parameter governs intervals between the
				completion of the previous reclamation cycle
				and the start of the next one.
				Expressed in seconds.";
				ngcliext:node-fmt "^$^ $% @@$n";
			}

			leaf flush-reclaimed-timer-wait-time {
				type uint16;
				default 25;
				description
				"This parameter controls how often the server
				initiates the lease reclamation procedure.
				Expressed in seconds.";
				ngcliext:node-fmt "^$^ $% @@$n";
			}

			leaf hold-reclaimed-time {
				type uint32;
				default 3600;
				description
				"This parameter governs how long the lease
				should be kept after it is reclaimed.
				This enables lease affinity when set to
				a non-zero value.
				Expressed in seconds.";
				ngcliext:node-fmt "^$^ $% @@$n";
			}

			leaf max-reclaim-leases {
				type uint32;
				default 100;
				description
				"This parameter specifies the maximum number
				of reclaimed leases that can be processed at
				one time. Zero means unlimited.";
				ngcliext:node-fmt "^$^ $% @@$n";
			}

			leaf max-reclaim-time {
				type uint16 {
				range "0..10000";
				}
				default 250;
				description
				"This parameter specifies an upper limit to
				the length of time a lease reclamation
				procedure can take. Zero means no time limit.
				Expressed in milliseconds.";
				ngcliext:node-fmt "^$^ $% @@$n";
			}

			leaf unwarned-reclaim-cycles {
				type uint16;
				default 5;
				description
				"This parameter specifies how many consecutive
				clean-up cycles must end with remaining leases
				to be processed before a warning is printed.
				The default is 5 cycles.";
				ngcliext:node-fmt "^$^ $% @@$n";
			}
		}

		container lease-database {

		    ngcliext:parent-fmt "^lease";

		    leaf type {
			type string;
			default "memfile";
			description
			    "The database type used to store the lease
			     information.  Currently only the type
			     'memfile' is supported.";
		    }

		    leaf name {
			type string;
			description
			    "Name of the DHCPv4 leases file on disk.
			     This should be a name ending in '.csv'.";
			ngcliext:node-fmt "$< filename @@$n";
		    }

		    leaf persist {
			type boolean;
			default true;
			description
			    "If set to TRUE, new leases and updates to
			     existing leases are written to the leases
			     file on disk.  If leases aren't written to
			     disk, no assurance can be made that leases
			     will persist across a server restart.";
			ngcliext:node-fmt "$< $% @@$n";
		    }

		    leaf lfc-interval {
			type uint32;
			default 3600;
			description
			    "The lfc-interval specifies the interval in
			     seconds at which the server will perform a
			     lease file cleanup to remove the unused,
			     historical information from the lease file.
			     The default is one hour (3600). Zero disables
			     the LFC operation.";
			ngcliext:node-fmt "$< $% @@$n";
		    }
		}

		container interfaces-config {
		    description
			"The interfaces-config holds configuration
			 information about each interface used by the
			 DHCPv4 server.";

		    ngcliext:parent-fmt "^interface";

		    list interfaces {
			key interface;
			description
			    "The interfaces is a list of interface names
			     or interface names with unicast addresses on
			     them on which the server will listen for DHCP
			     requests.";

			ngcliext:node-fmt "$< listen @{interface}$n";

			leaf interface {
			    type ngcom:if-identifier-63;
			    description
				"The name of an interface on which the
				 server will listen for IPv4 DHCP
				 requests.";
			}
		    }

		    leaf dhcp-socket-type {
			type string;
			default "raw";
			description
			    "Sockets used for listening on the set of
			     interfaces will be opened as either'raw' IP
			     sockets, or 'udp' sockets.";
			ngcliext:node-fmt "$< socket @@$n"; 
		    }
		}

		list subnet4 {
		    key subnet;
		    unique id;
		    description
			"An IPv4 subnet configuration within the DHCPv4
			server.";

		    ngcliext:node-fmt "^subnet @{subnet}$n";
		    ngcliext:pre-children-op "push";

		    leaf subnet {
			type inet:ipv4-prefix;
			description
			    "The IPv4 subnet prefix.";
		    }

		    leaf authoritative {
			type boolean;
			description
			    "Per-subnet flag to determine whether to send a
			     NAK in response to requests by clients for
			     unknown IP addresses.";
		        ngcliext:node-fmt "^$% @@$n";
		    }

		    leaf id {
			type uint32 {
			range "1..max";
			}
			mandatory true;
			description
			    "Manually assigned subnet id.";
			ngcliext:node-fmt "^$% @@$n";
		    }

		    leaf interface {
			type ngcom:if-identifier-63;
			mandatory true;
			description
			    "Interface on which subnet is located.";
			ngcliext:node-fmt "^$% @@$n";
		    }

		    uses kea-dhcp4-option-group;

		    list pools {
			key pool;
			description
			    "A list of leased address pools.  Each pool
			     is specified as a start and optional end IPv4
			     addresses, or as an IPv4 address and prefix.";

			ngcliext:node-fmt "^pool @{pool}$n";
			ngcliext:pre-children-op "push";

			leaf pool {
			    type ipv4-prefix-or-range;
			    description
				"A pool is specified as a start and
				 optional end IPv4 addresses, or as an
				 IPv4 address and prefix.";
			}

			uses kea-dhcp4-option-group;
		    }

		    list reservations {
			key ip-address;
			unique hw-address;

			description
			    "List of host reservations.";

			ngcliext:node-fmt "^reservation @{ip-address}$n";
			ngcliext:pre-children-op "push";

			leaf ip-address {
			    type inet:ipv4-address;
			    description
				"The IPv4 address for the host.";
			}

			leaf hw-address {
			    type yang:mac-address;
			    mandatory true;
			    description
				"The host's MAC address.";
			    ngcliext:node-fmt "^mac-address @@$n";
			}

			leaf hostname {
			    type inet:domain-name;
			    description
				"The host name of the identified host.";
			    ngcliext:node-fmt "^$% @@$n";
			}

			uses kea-dhcp4-option-group;
		    }
		}
	    }
	}
    }

    container kea-state {

	config "false";
	description
	    "Kea state.";

	container dhcp4-server {
	    description
		"DHCPv4 state.";

	    container leases {
		description
		    "List of Kea DHCPv4 leases.";

		list lease {
		    key ip-address;
		    description
			"Kea DHCPv4 lease.";

		    leaf ip-address {
			type inet:ipv4-address;
			description
			    "Lease IP address.";
		    }

		    leaf hw-address {
			type yang:mac-address;
			mandatory true;
			description
			    "Lease MAC address.";
		    }

		    leaf valid-lifetime {
			type uint32;
			mandatory true;
			description
			    "The valid duration for an assigned lease in
			    seconds.";
		    }

		    leaf cltt {
			type uint32;
			mandatory true;
			description
			    "Lease client last transmission time";
		    }

		    leaf subnet-id {
			type uint32;
			mandatory true;
			description
			    "Lease subnet id.";
		    }

		    leaf client-id {
			type string;
			description
			    "Lease identifying client-id address.";
		    }

		    leaf fqdn-fwd {
			type boolean;
			description
			    "Forward DNS update flag.";
		    }

		    leaf fqdn-rev {
			type boolean;
			description
			    "Reverse DNS update flag.";
		    }

		    leaf hostname {
			type string;
			description
			    "Client hostname.";
		    }

		    leaf state {
			type kea-lease-state;
			description
			    "Lease state.";
		    }
		}
	    }
	}
    }
}
