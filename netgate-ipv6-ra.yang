module netgate-ipv6-ra {

    yang-version "1.1";

    namespace "urn:netgate:xml:yang:netgate-ipv6-ra";
    prefix "ngipv6ra";

    import ietf-inet-types {
	prefix "inet";
    }

    import netgate-cli-extensions {
	prefix "ngcliext";
    }

    import netgate-interface {
	prefix "ngif";
    }

    organization "Netgate";

    contact "Web: <http://www.netgate.com>";

    description
	"This YANG module provides a data model for IPv6 Router Advertisements.
	 The model is duplicated directly, to the extent possible, from the
	 IETF IPv6 Router Advertisements data model introduced by RFC 8349.

	 Copyright 2022,2026 Rubicon Communications, LLC.";

    revision 2026-06-01 {
	description
	    "TNSR Release 26.06.";
    }

    revision 2023-02-01 {
	description
	    "TNSR Release 23.02.";
    }

    augment "/ngif:interfaces-config/ngif:interface/ngif:ipv6" {
	description
	    "Augments interface configuration with parameters of IPv6
	     Router Advertisements.";

	container ipv6-router-advertisements {
	    description
		"Support for IPv6 Router Advertisements.";

	    ngcliext:context "intf-interfaces";
	    ngcliext:node-fmt "$< router-advertisements$n";
	    ngcliext:pre-children-op "push";

	    leaf send-advertisements {
		type boolean;
		default "false";
		description
		    "A flag indicating whether or not the router sends
		     periodic Router Advertisements and responds to
		     Router Solicitations.";
		reference
		    "RFC 4861: Neighbor Discovery for IP version 6 (IPv6)
			       - AdvSendAdvertisements";
		ngcliext:node-fmt "^$% @@$n";
	    }

	    leaf max-rtr-adv-interval {
		type uint16 {
		    range "4..65535";
		}
		units "seconds";
		default "600";
		description
		    "The maximum time allowed between sending unsolicited
		     multicast Router Advertisements from the interface.";
		ngcliext:node-fmt "^$% @@$n";
	    }

	    leaf min-rtr-adv-interval {
		type uint16 {
		    range "3..1350";
		}
		units "seconds";
		must ". <= 0.75 * ../max-rtr-adv-interval" {
		    description
			"The value MUST NOT be greater than 75% of
			 'max-rtr-adv-interval'.";
		}
		description
		    "The minimum time allowed between sending unsolicited
		     multicast Router Advertisements from the interface.

		     The default value to be used operationally if this
		     leaf is not configured is determined as follows:

		     - if max-rtr-adv-interval >= 9 seconds, the default
		       value is 0.33 * max-rtr-adv-interval;

		     - otherwise, it is 0.75 * max-rtr-adv-interval.";
		ngcliext:node-fmt "^$% @@$n";
	    }

	    leaf managed-flag {
		type boolean;
		default "false";
		description
		    "The value to be placed in the 'Managed address
		     configuration' flag field in the Router
		     Advertisement.";
		ngcliext:node-fmt "^$% @@$n";
	    }

	    leaf other-config-flag {
		type boolean;
		default "false";
		description
		    "The value to be placed in the 'Other configuration'
		     flag field in the Router Advertisement.";
		ngcliext:node-fmt "^$% @@$n";
	    }

	    /* Currently, the value cannot be configured. Instead, the value of
	     * IPv6 MTU configured on the corresponding interface will be used.
	     */
	    /*
	    leaf link-mtu {
		type uint32;
		default "0";
		description
		    "The value to be placed in MTU options sent by the
		     router.  A value of zero indicates that no MTU options
		     are sent.";
		ngcliext:node-fmt "^$% @@$n";
	    }
	    */

	    /* Currently, the value cannot be configured. Instead, zero will be
	     * used.
	     */
	    /*
	    leaf reachable-time {
		type uint32 {
		    range "0..3600000";
		}
		units "milliseconds";
		default "0";
		description
		    "The value to be placed in the Reachable Time field in
		     the Router Advertisement messages sent by the router.
		     A value of zero means unspecified (by this router).";
		ngcliext:node-fmt "^$% @@$n";
	    }
	    */

	    /* Currently, the value cannot be configured. Instead, zero will be
	     * used.
	     */
	    /*
	    leaf retrans-timer {
		type uint32;
		units "milliseconds";
		default "0";
		description
		    "The value to be placed in the Retrans Timer field in
		     the Router Advertisement messages sent by the router.
		     A value of zero means unspecified (by this router).";
		ngcliext:node-fmt "^$% @@$n";
	    }
	    */

	    /* Currently, the value cannot be configured. Instead, 64 will be
	     * used.
	     */
	    /*
	    leaf cur-hop-limit {
		type uint8;
		description
		    "The value to be placed in the Cur Hop Limit field in
		     the Router Advertisement messages sent by the router.
		     A value of zero means unspecified (by this router).

		     If this parameter is not configured, the device SHOULD
		     use the IANA-specified value for the default IPv4
		     Time to Live (TTL) parameter that was in effect at the
		     time of implementation.";
		ngcliext:node-fmt "^$% @@$n";
	    }
	*/

	    leaf default-lifetime {
		type uint16 {
		    range "0..65535";
		}
		units "seconds";
		description
		    "The value to be placed in the Router Lifetime field of
		     Router Advertisements sent from the interface, in
		     seconds.  It MUST be either zero or between
		     max-rtr-adv-interval and 9000 seconds.  A value of zero
		     indicates that the router is not to be used as a
		     default router.  These limits may be overridden by
		     specific documents that describe how IPv6 operates over
		     different link layers.

		     If this parameter is not configured, the device SHOULD
		     use a value of 3 * max-rtr-adv-interval.";
		ngcliext:node-fmt "^$% @@$n";
	    }

	    container prefix-list {
		description
		    "Support for prefixes to be placed in Prefix
		     Information options in Router Advertisement messages
		     sent from the interface.

		     Prefixes that are advertised by default but do not
		     have their entries in the child 'prefix' list are
		     advertised with the default values of all parameters.

		     The link-local prefix SHOULD NOT be included in the
		     list of advertised prefixes.";

		list prefix {
		    key "prefix-spec";
		    description
			"Support for an advertised prefix entry.";

		    ngcliext:node-fmt "^$% @{prefix-spec}$n";
		    ngcliext:pre-children-op "push";

		    leaf prefix-spec {
			type inet:ipv6-prefix;
			description
			    "IPv6 address prefix.";
		    }

		    choice control-adv-prefixes {
			default "advertise";
			description
			    "Either (1) the prefix is explicitly removed from
			     the set of advertised prefixes or (2) the
			     parameters with which the prefix is advertised are
			     specified (default case).";

			leaf no-advertise {
			    type empty;
			    description
				"The prefix will not be advertised.

				 This can be used for removing the prefix from
				 the default set of advertised prefixes.";
			    ngcliext:node-fmt "^$%$n";
			}

			case advertise {
			    leaf valid-lifetime {
				type uint32;
				units "seconds";
				default "2592000";
				description
				    "The value to be placed in the Valid
				     Lifetime in the Prefix Information option.
				     The designated value of all 1's
				     (0xffffffff) represents infinity.";
				ngcliext:node-fmt "^$% @@$n";
			    }

			    leaf on-link-flag {
				type boolean;
				default "true";
				description
				    "The value to be placed in the on-link flag
				     ('L-bit') field in the Prefix Information
				     option.";
				ngcliext:node-fmt "^$% @@$n";
			    }

			    leaf preferred-lifetime {
				type uint32;
				units "seconds";
				must ". <= ../valid-lifetime" {
				    description
					"This value MUST NOT be greater than
					 valid-lifetime.";
				    error-message
					"The preferred lifetime for an advertised IPv6 prefix cannot be greater than the valid lifetime.";
				}
				default "604800";
				description
				    "The value to be placed in the Preferred
				     Lifetime in the Prefix Information option.
				     The designated value of all 1's
				     (0xffffffff) represents infinity.";
				ngcliext:node-fmt "^$% @@$n";
			    }

			    leaf autonomous-flag {
				type boolean;
				default "true";
				description
				    "The value to be placed in the Autonomous
				     Flag field in the Prefix Information
				     option.";
				ngcliext:node-fmt "^$% @@$n";
			    }
			}
		    }
		}
	    }
	}
    }

    augment "/ngif:interfaces-state/ngif:interface/ngif:ipv6" {
	description
	    "Augments interface state data with parameters of IPv6
	     Router Advertisements.";

	container ipv6-router-advertisements {
	    description
		"Parameters of IPv6 Router Advertisements.";

	    leaf send-advertisements {
		type boolean;
		description
		    "A flag indicating whether or not the router sends
		     periodic Router Advertisements and responds to
		     Router Solicitations.";
	    }

	    leaf max-rtr-adv-interval {
		type uint16 {
		    range "4..1800";
		}
		units "seconds";
		description
		    "The maximum time allowed between sending unsolicited
		     multicast Router Advertisements from the interface.";
	    }

	    leaf min-rtr-adv-interval {
		type uint16 {
		    range "3..1350";
		}
		units "seconds";
		description
		    "The minimum time allowed between sending unsolicited
		     multicast Router Advertisements from the interface.";
	    }

	    leaf managed-flag {
		type boolean;
		description
		    "The value that is placed in the 'Managed address
		     configuration' flag field in the Router Advertisement.";
	    }

	    leaf other-config-flag {
		type boolean;
		description
		    "The value that is placed in the 'Other configuration' flag
		     field in the Router Advertisement.";
	    }

	    leaf link-mtu {
		type uint32;
		description
		    "The value that is placed in MTU options sent by the
		     router.  A value of zero indicates that no MTU options
		     are sent.";
	    }

	    leaf reachable-time {
		type uint32 {
		    range "0..3600000";
		}
		units "milliseconds";
		description
		    "The value that is placed in the Reachable Time field in
		     the Router Advertisement messages sent by the router.  A
		     value of zero means unspecified (by this router).";
	    }

	    leaf retrans-timer {
		type uint32;
		units "milliseconds";
		description
		    "The value that is placed in the Retrans Timer field in the
		     Router Advertisement messages sent by the router.  A value
		     of zero means unspecified (by this router).";
	    }

	    leaf cur-hop-limit {
		type uint8;
		description
		    "The value that is placed in the Cur Hop Limit field in the
		     Router Advertisement messages sent by the router.  A value
		     of zero means unspecified (by this router).";
	    }

	    leaf default-lifetime {
		type uint16 {
		    range "0..9000";
		}
		units "seconds";
		description
		    "The value that is placed in the Router Lifetime field of
		     Router Advertisements sent from the interface, in seconds.
		     A value of zero indicates that the router is not to be
		     used as a default router.";
	    }

	    container prefix-list {
		description
		    "A list of prefixes that are placed in Prefix Information
		     options in Router Advertisement messages sent from the
		     interface.

		     By default, these are all prefixes that the router
		     advertises via routing protocols as being on-link for the
		     interface from which the advertisement is sent.";

		list prefix {
		    key "prefix-spec";
		    description
			"Advertised prefix entry and its parameters.";

		    leaf prefix-spec {
			type inet:ipv6-prefix;
			description
			    "IPv6 address prefix.";
		    }

		    leaf valid-lifetime {
			type uint32;
			units "seconds";
			description
			    "The value that is placed in the Valid Lifetime in
			     the Prefix Information option.  The designated
			     value of all 1's (0xffffffff) represents infinity.

			     An implementation SHOULD keep this value constant
			     in consecutive advertisements, except when it is
			     explicitly changed in configuration.";
		    }

		    leaf valid-lifetime-expires {
			type int32;
			units "seconds";
			description
			    "If positive, the number of seconds in which valid
			     lifetime expires. If negative, the number of
			     seconds passed since valid lifetime has expired.
			     Zero represents never.";
		    }

		    leaf on-link-flag {
			type boolean;
			description
			    "The value that is placed in the on-link flag
			     ('L-bit') field in the Prefix Information
			     option.";
		    }

		    leaf preferred-lifetime {
			type uint32;
			units "seconds";
			description
			    "The value that is placed in the Preferred Lifetime
			     in the Prefix Information option, in seconds.  The
			     designated value of all 1's (0xffffffff)
			     represents infinity.

			     An implementation SHOULD keep this value constant
			     in consecutive advertisements, except when it is
			     explicitly changed in configuration.";
		    }

		    leaf preferred-lifetime-expires {
			type int32;
			units "seconds";
			description
			    "If positive, the number of seconds in which
			     preferred lifetime expires. If negative, the
			     number of seconds passed since preferred lifetime
			     has expired. Zero represents never.";
		    }

		    leaf autonomous-flag {
			type boolean;
			description
			    "The value that is placed in the Autonomous Flag
			     field in the Prefix Information option.";
		    }

		    leaf decrement-lifetime-flag {
			type boolean;
			description
			    "Indicates whether decrement valid lifetime and
			     preferred lifetime.";
		    }
		}
	    }

	    container initial-advertisements {
		description
		    "Initial Router Advertisement messages sent from the
		     interface.";

		leaf count {
		    type uint32;
		    description
			"The number of initial Router Advertisement
			 messages to be sent.";
		}

		leaf interval {
		    type uint32;
		    units "seconds";
		    description
			"The number of seconds between initial Router
			 Advertisement messages.";
		}

		leaf all-sent-flag {
		    type boolean;
		    description
			"Indicates whether all initial Router Advertisement
			 messages have been sent.";
		}
	    }

	    container timers {
		description
		    "Timers of Router Advertisement messages that have been
		     sent from the interface or are planned to be sent.";

		leaf last-solicited-time {
		    type uint32;
		    units "seconds";
		    description
			"The number of seconds since the last time a solicited
			 Router Advertisement message was sent. Zero represents
			 never";
		}

		leaf last-unsolicited-time {
		    type uint32;
		    units "seconds";
		    description
			"The number of seconds since the last time an
			 unsolicited Router Advertisement message was sent.
			 Zero represents never";
		}

		leaf next-unsolicited-time {
		    type uint32;
		    units "seconds";
		    description
			"The number of seconds within which next time an
			 unsolicited Router Advertisement message will be sent.
			 Zero represents never";
		}
	    }

	    container counters {
		description
		    "Counters of Router Advertisement messages that have been
		     sent from the interface and Router Solicitation
		     messages that have been received on the interface.";

		leaf advertisements-sent {
		    type uint32;
		    description
			"The number of Router Advertisement messages that have
			 been sent.";
		}

		leaf solicitations-received {
		    type uint32;
		    description
			"The number of Router Solicitation messages that have
			 been received.";
		}

		leaf solicitations-dropped {
		    type uint32;
		    description
			"The number of Router Solicitation messages that have
			 been dropped.";
		}
	    }
	}
    }
}
