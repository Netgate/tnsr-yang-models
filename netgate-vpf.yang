module netgate-vpf {

    yang-version 1.1;

    namespace "urn:netgate:xml:yang:netgate-vpf";
    prefix "ngvpf";

    import clixon-lib {
	prefix "cl";
    }

    import ietf-inet-types {
	prefix "inet";
    }

    import netgate-cli-extensions {
	prefix "ngcliext";
    }

    import netgate-common {
	prefix "ngcom";
    }

    import netgate-route-table {
	prefix "ngrttab";
    }

    organization "Netgate";

    contact "Web: <http://www.netgate.com>";

    description
	"This YANG module provides a Netgate-defined data-model
	 for Netbsd Packet Filters.

	 Copyright 2024, 2025 Rubicon Communications, LLC.";

    revision 2026-10-03 {
	description
	    "Restrict NPT66 NAT rule translation prefix to /112 or
	     shorter. A longer prefix leaves no 16-bit word of the
	     translated address to absorb the RFC 6296 checksum
	     adjustment.";
    }

    revision 2026-10-02 {
	description
	    "Restrict filter rule return-rst and return-icmp to 'in'
	     block rules.";
    }

    revision 2026-10-01 {
	description
	    "TNSR Release 26.10.";
    }

    revision 2025-10-02 {
	description
	    "TNSR Release 25.10.";
    }

    revision 2025-06-05 {
	description
	    "TNSR Release 25.06.";
    }

    revision 2025-02-02 {
	description
	    "TNSR Release 25.02.";
    }

    revision 2024-10-04 {
	description
	    "TNSR Release 24.10.";
    }

    typedef vpf-nat-direction {
	type enumeration {
	    enum in {
		value 1;
		description "Inbound destination translation on packet receive.";

	    }

	    enum out {
		value 2;
		description "Outbound source translation on packet transmit.";
	    }
	}
    }

    typedef vpf-filter-direction {
	type enumeration {
	    enum in {
		value 1;
		description "Inbound filter on packet receive.";
	    }

	    enum out {
		value 2;
		description "Outbound filter on packet transmit.";
	    }
	}
    }

    typedef vpf-nat-algorithm {
	type enumeration {
	    enum one-to-one {
		description
		    "Use static 1:1 mapping.";
	    }

	    enum netmap {
		description
		    "Network address mapping from one segment to another,
		     leaving the host part as-is.  The new address is
		     computed as following:
			 addr = net-addr | (orig-addr & ~mask).";
	    }

	    enum "src-ip-hash" {
		description
		    "The translation address for a new connection is
		     selected based on a hash of the original source
		     address.  This algorithm attempts to keep all
		     connections of particular client associated with
		     the same translation address.";
	    }

	    enum "ip-hash" {
		description
		    "The translation address for a new connection is
		     selected based on a hash of the original source
		     and destination addresses.  This algorithm
		     attempts to keep all connections of particular
		     client to particular server associated with
		     the same translation address.
		     This is the default algorithm.";
	    }

	    enum "round-robin" {
		description
		    "The translation address for each new connection is
		     selected on a round-robin basis.";
	    }

	    enum "npt66" {
		description
		    "IPv6-to-IPv6 network prefix translation (NPTv6).";
	    }
	}
    }

    grouping vpf-connection-filter {
	description "VPF connection filter";

	leaf invert {
	    type boolean;
	    description "Invert match.";
	}

	leaf filter-only {
	    type boolean ;
	    description "Match only filter connections.";
	}

	leaf nat-only {
	    type boolean;
	    description "Match only NAT connections.";
	}

	leaf interface-bound-only {
	    type boolean ;
	    description "Match only connections bound to interface.";
	}

	leaf route-table-bound-only {
	    type boolean;
	    description "Match only connections bound to route table.";
	}

	leaf post-nat-only {
	    type boolean;
	    description "Match only post-NAT connections.";
	}

	leaf block-only {
	    type boolean;
	    description "Match only block connections.";
	}

	choice source-prefix-or-address {
	    case prefix {
		leaf source-prefix {
		    type inet:ip-prefix;
		    description "Source address prefix.";
		}
	    }

	    case address {
		leaf source-address {
		    type inet:ip-address;
		    description "Source address prefix.";
		}
	    }
	}

	choice not-source-prefix-or-address {
	    case not-prefix {
		leaf not-source-prefix {
		    type inet:ip-prefix;
		    description "Source address prefix (exclusion).";
		}
	    }

	    case not-address {
		leaf not-source-address {
		    type inet:ip-address;
		    description "Source address prefix (exclusion).";
		}
	    }
	}

	choice destination-prefix-or-address {
	    case prefix {
		leaf destination-prefix {
		    type inet:ip-prefix;
		    description "Destination address prefix.";
		}
	    }

	    case address {
		leaf destination-address {
		    type inet:ip-address;
		    description "Destination address prefix.";
		}
	    }
	}

	choice not-destination-prefix-or-address {
	    case not-prefix {
		leaf not-destination-prefix {
		    type inet:ip-prefix;
		    description "Destination address prefix (exclusion).";
		}
	    }

	    case not-address {
		leaf not-destination-address {
		    type inet:ip-address;
		    description "Destination address prefix (exclusion).";
		}
	    }
	}

	choice translation-prefix-or-address {
	    case prefix {
		leaf translation-prefix {
		    type inet:ip-prefix;
		    description "Translation address prefix.";
		}
	    }

	    case address {
		leaf translation-address {
		    type inet:ip-address;
		    description "Translation address prefix.";
		}
	    }
	}

	choice not-translation-prefix-or-address {
	    case not-prefix {
		leaf not-translation-prefix {
		    type inet:ip-prefix;
		    description "Translation address prefix (exclusion).";
		}
	    }

	    case not-address {
		leaf not-translation-address {
		    type inet:ip-address;
		    description "Translation address prefix (exclusion).";
		}
	    }
	}

	leaf source-id {
	    type uint32;
	    description "Source identifier.";
	}

	leaf not-source-id {
	    type uint32;
	    description "Source identifier (exclusion).";
	}

	leaf destination-id {
	    type uint32;
	    description "Destination identifier.";
	}

	leaf not-destination-id {
	    type uint32;
	    description "Destination identifier (exclusion).";
	}

	leaf translation-id {
	    type uint32;
	    description "Translation identifier.";
	}

	leaf not-translation-id {
	    type uint32;
	    description "Translation identifier (exclusion).";
	}

	leaf protocol {
	    type ngcom:ip-protocol-name-or-number;
	    description "IP protocol.";
	}

	leaf not-protocol {
	    type ngcom:ip-protocol-name-or-number;
	    description "IP protocol (exclusion).";
	}

	leaf source-route-table {
	    type ngcom:rt-identifier-15;
	    description "Source VRF name.";
	}

	leaf not-source-route-table {
	    type ngcom:rt-identifier-15;
	    description "Source VRF name (exclusion).";
	}

	leaf destination-route-table {
	    type ngcom:rt-identifier-15;
	    description "Destination VRF name.";
	}

	leaf not-destination-route-table {
	    type ngcom:rt-identifier-15;
	    description "Destination VRF name (exclusion).";
	}

	choice bound-to {
	    description "Binding interface or VRF.";

	    case interface {
		leaf bound-to-interface {
		    type ngcom:if-identifier-63;
		    description "Binding interface.";
		}
	    }

	    case route-table {
		leaf bound-to-route-table {
		    type ngcom:rt-identifier-15;
		    description "Binding route table.";
		}
	    }
	}

	choice not-bound-to {
	    description "Binding interface or VRF (exclusion).";

	    case not-interface {
		leaf not-bound-to-interface {
		    type ngcom:if-identifier-63;
		    description "Binding interface (exclusion).";
		}
	    }

	    case not-route-table {
		leaf not-bound-to-route-table {
		    type ngcom:rt-identifier-15;
		    description "Binding route table (exclusion).";
		}
	    }
	}
    }

    typedef vpf-connection-state-generic {
	type enumeration {
	    enum new {
		value 0;
		description "New.";
	    }

	    enum established {
		value 1;
		description "Established.";
	    }

	}
    }

    typedef vpf-connection-state-tcp {
	type enumeration {
	    enum closed {
		value 0;
		description "CLOSED.";
	    }

	    enum syn-sent {
		value 1;
		description "SYN-SENT.";
	    }

	    enum sim-syn-sent {
		value 2;
		description "SIM-SYN-SENT.";
	    }

	    enum syn-received {
		value 3;
		description "SYN-RCVD.";
	    }

	    enum established {
		value 4;
		description "ESTAB.";
	    }

	    enum fin-sent {
		value 5;
		description "FIN-SENT.";
	    }

	    enum fin-received {
		value 6;
		description "FIN-RCVD.";
	    }

	    enum close-wait {
		value 7;
		description "CLOSE-WAIT.";
	    }

	    enum fin-wait {
		value 8;
		description "FIN-WAIT.";
	    }

	    enum closing {
		value 9;
		description "CLOSING.";
	    }

	    enum last-ack {
		value 10;
		description "LAST-ACK.";
	    }

	    enum time-wait {
		value 11;
		description "TIME-WAIT.";
	    }

	    enum syn-sent-rem-syn-acked {
		value 12;
		description "SYN-SENT-REM-SYN-ACK.";
	    }

	}
    }

    typedef vpf-connection-direction {
	type enumeration {
	    enum in {
		value 1;
		description "In.";
	    }

	    enum out {
		value 2;
		description "Out.";
	    }
	}
    }

    grouping vpf-tcp-context {
	description "VPF TCP tracking context.";

	leaf end {
	    type uint32;
	}

	leaf maxend {
	    type uint32;
	}

	leaf maxwin {
	    type uint32;
	}

	leaf wscale {
	    type int32;
	}
    }

    grouping vpf-connection-key {
	description "VPF connection key.";
	leaf rx-route-table {
	    type leafref {
		path "/ngrttab:route-table-config" +
		    "/ngrttab:static-routes" +
		    "/ngrttab:route-table/ngrttab:name";
	    }
	    description "RX route-table name.";
	}

	leaf direction {
	    type vpf-connection-direction;
	    description "Direction.";
	}

	leaf source-address {
	    type inet:ip-address;
	    description "Source address.";
	}

	leaf destination-address {
	    type inet:ip-address;
	    description "Destination address.";
	}

	leaf source-id {
	    type uint32;
	    description "Source identifier.";
	}

	leaf destination-id {
	    type uint32;
	    description "Destination identifier.";
	}
    }

    grouping vpf-connection-details {
	description "VPF connection details.";

	leaf thread-index {
	    type uint32;
	    description "Thread index this connection belongs to.";
	}

	leaf is-pass {
	    type boolean;
	    description "Indicates whether this is a 'pass' connection.";
	}

	leaf is-block {
	    type boolean;
	    description "Indicates whether this is a 'block' connection.";
	}

	leaf is-post-nat {
	    type boolean;
	    description "Indicates whether this is a post-NAT filter connection.";
	}

	leaf is-block-return-rst {
	    type boolean;
	    description "Indicates whether this block connection returns TCP RST on block.";
	}

	leaf is-block-return-icmp {
	    type boolean;
	    description "Indicates whether this block connection returns ICMP error on block.";
	}

	leaf protocol {
	    type ngcom:ip-protocol-name-or-number;
	    description "IP protocol.";
	}

	choice connection-state {
	    description "Connection state.";

	    case generic {
		leaf generic-state {
		    type vpf-connection-state-generic;
		    description "Generic connection state.";
		}
	    }

	    case tcp {
		leaf tcp-state {
		    type vpf-connection-state-tcp;
		    description "TCP connection state.";
		}
	    }
	}

	choice protocol-tracking-context {
	    description "Protocol specific tracking context.";

	    case tcp-tracking-context {

		container tcp-forward-tracking-context {
		    description "Forward TCP tracking context.";
		    uses vpf-tcp-context;
		}

		container tcp-backward-tracking-context {
		    description "Backward TCP tracking context.";
		    uses vpf-tcp-context;
		}
	    }
	}

	leaf last-heard-ago {
	    description "Time since last packet seen.";

	    type decimal64 {
		fraction-digits 2;
	    }
	}

	choice expiry-time {

	    case active {
		leaf expires-in {
		    description "Time to connection expiry.";

		    type decimal64 {
			fraction-digits 2;
		    }
		}
	    }

	    case expired {
		leaf expired-ago {
		    description "Time since connection expiry.";

		    type decimal64 {
			fraction-digits 2;
		    }
		}
	    }
	}

	leaf last-lru-update {
	    description "Time since last LRU update.";

	    type decimal64 {
		fraction-digits 2;
	    }
	}

	choice bound-to {
	    description "Binding interface or VRF.";

	    case interface {
		leaf bound-to-interface {
		    type ngcom:if-identifier-63;
		    description "Binding interface.";
		}
	    }

	    case table {
		leaf bound-to-route-table {
		    type leafref {
			path "/ngrttab:route-table-config" +
			    "/ngrttab:static-routes" +
			    "/ngrttab:route-table/ngrttab:name";
		    }
		    description "Binding VRF name.";
		}
	    }
	}


	leaf translation-address {
	    type inet:ip-address;
	    description "Translation address.";
	}

	leaf translation-id {
	    type uint32;
	    description "Translation identifier.";
	}

	container forward-key {
	    uses vpf-connection-key;
	    description "Forward key.";
	}

	container backward-key {
	    uses vpf-connection-key;
	    description "Backward key.";
	}

	leaf packets-fw {
	    type uint64;
	    description
		"Number of forward packets matched by this connection.";
	}

	leaf bytes-fw {
	    type uint64;
	    description
		"Number of forward bytes matched by this connection.";
	}

	leaf packets-bk {
	    type uint64;
	    description
		"Number of backward packets matched by this connection.";
	}

	leaf bytes-bk {
	    type uint64;
	    description
		"Number of backward bytes matched by this connection.";
	}
    }

    typedef vpf-select-mmdb-field {
	type enumeration {
	    enum asn {
		value 1;
		description "Match on the asn field.";
	    }
	    enum alpha2code {
		value 2;
		description "Match on the alpha2code field.";
	    }
	    enum region {
		value 3;
		description "Match on the region field.";
	    }
	    enum city {
		value 4;
		description "Match on the city field.";
	    }
	}
    }

    typedef vpf-select-csv-field {
	type enumeration {
	    enum u0 {
		value 0;
		description "Match as a uint32 on field 0.";
	    }
	    enum u1 {
		value 1;
		description "Match as a uint32 on field 1.";
	    }
	    enum u2 {
		value 2;
		description "Match as a uint32 on field 2.";
	    }
	    enum u3 {
		value 3;
		description "Match as a uint32 on field 3.";
	    }
	    enum u4 {
		value 4;
		description "Match as a uint32 on field 4.";
	    }
	    enum u5 {
		value 5;
		description "Match as a uint32 on field 5.";
	    }
	    enum u6 {
		value 6;
		description "Match as a uint32 on field 6.";
	    }
	    enum u7 {
		value 7;
		description "Match as a uint32 on field 7.";
	    }
	    enum u8 {
		value 8;
		description "Match as a uint32 on field 8.";
	    }
	    enum u9 {
		value 9;
		description "Match as a uint32 on field 9.";
	    }
	    enum s0 {
		value 10;
		description "Match as a string on field 0.";
	    }
	    enum s1 {
		value 11;
		description "Match as a string on field 1.";
	    }
	    enum s2 {
		value 12;
		description "Match as a string on field 2.";
	    }
	    enum s3 {
		value 13;
		description "Match as a string on field 3.";
	    }
	    enum s4 {
		value 14;
		description "Match as a string on field 4.";
	    }
	    enum s5 {
		value 15;
		description "Match as a string on field 5.";
	    }
	    enum s6 {
		value 16;
		description "Match as a string on field 6.";
	    }
	    enum s7 {
		value 17;
		description "Match as a string on field 7.";
	    }
	    enum s8 {
		value 18;
		description "Match as a string on field 8.";
	    }
	    enum s9 {
		value 19;
		description "Match as a string on field 9.";
	    }
	}    	
    }

    typedef vpf-select-comparison {
	type enumeration {
	    enum eq {
		description "equals match.";
	    }
	    enum ne {
		description "Not-equals match.";
	    }
	    enum lt {
		description "Less-than match.";
	    }
	    enum le {
		description "Less-than-or-equal match.";
	    }
	    enum gt {
		description "Greater-than match.";
	    }
	    enum ge {
		description "Greater-than-or-equal match.";
	    }
	}
    }

    rpc vpf-connections-get {
	description "Get VPF connections.";

	input {
	    leaf thread-index {
		type uint32;
		description "Thread index";
	    }

	    leaf not-thread-index {
		type uint32;
		description "Thread index (exclusion)";
	    }

	    leaf limit {
		description "Maximum number of connections returned";
		type uint32 {
		    range "1..max";
		}
		default 100;
	    }

	    uses vpf-connection-filter;
	}

	output {
	    list connection {
		uses vpf-connection-details;
	    }
	}
    }

    rpc vpf-ha-export-trigger {
	description "Trigger VPF HA export.";

	output {
	    leaf success {
		description "Success of the operation";
		type boolean;
	    }
	}
    }

    rpc vpf-connections-clear {
	description "Clear VPF connections.";

	input {
	    leaf thread-index {
		type uint32;
		description "Thread index";
		default 4294967295;
	    }

	    leaf not-thread-index {
		type uint32;
		description "Thread index (exclusion)";
	    }

	    uses vpf-connection-filter;
	}

	output {
	    leaf ip4-connections-cleared {
		type uint32;
	    }

	    leaf ip6-connections-cleared {
		type uint32;
	    }
	}
    }

    grouping vpf-connection-statistics-by-protocol {
	description "VPF connection statistics by IP protocol";

	leaf tcp {
	    type uint32;
	    description "TCP connections.";
	}

	leaf udp {
	    type uint32;
	    description "UDP connections.";
	}

	leaf icmp {
	    type uint32;
	    description "ICMP connections.";
	}

	leaf other {
	    type uint32;
	    description "other connections.";
	}
    }

    grouping vpf-connection-statistics-by-type {
	description "VPF connection statistics by type";

	container filter {
	    uses vpf-connection-statistics-by-protocol;
	}

	container nat-endpoint-dependent {
	    uses vpf-connection-statistics-by-protocol;
	}

	container nat-endpoint-independent {
	    uses vpf-connection-statistics-by-protocol;
	}
    }

    grouping vpf-connection-statistics-by-timer-status {
	description "VPF connection statistics by timer status";

	container active {
	    uses vpf-connection-statistics-by-type;
	}

	container expired {
	    uses vpf-connection-statistics-by-type;
	}
    }

    rpc vpf-connection-statistics-get {
	output {
	    list per-thread {
		leaf thread-index {
		    type uint32;
		}

		container ip4 {
		    uses vpf-connection-statistics-by-timer-status;
		}

		container ip6 {
		    uses vpf-connection-statistics-by-timer-status;
		}
	    }
	}
    }

    grouping vpf-endpoint {
	description
	    "VPF source or destination endpoint";

	leaf inverted {
	    type boolean;
	    description
		"If true, endpoint matching is inverted.";
	    ngcliext:node-op "bool";
	    ngcliext:node-fmt "|$< $%$n";
	}

	choice type {
	    description
		"VPF source or destination endpoint IP addresses";

	    case ipv4-prefix {
		leaf ipv4-prefix {
		    type inet:ipv4-prefix;
		    ngcliext:node-fmt "$< $% @@$n";
		}
	    }

	    case ipv6-prefix {
		leaf ipv6-prefix {
		    type inet:ipv6-prefix;
		    ngcliext:node-fmt "$< $% @@$n";
		}
	    }

	    case prefix-table-name {
		leaf prefix-table-name {
		    type leafref {
			path "/ngvpf:vpf-config"
			    + "/ngvpf:prefix-tables"
			    + "/ngvpf:table"
			    + "/ngvpf:name";
		    }
		    ngcliext:node-fmt "$< prefix-table @@$n";
		}
	    }

	    case if-name {
		leaf if-name {
		    type ngcom:if-identifier-63;
		    ngcliext:node-fmt "$< ifaddrs @@$n";
		}
	    }
	}

	choice port-type {
	    description "VPF source or destination ports";

	    case port-range {
		leaf port-min {
		    type uint16;
		    description
			"The first source port in a range.";
			ngcliext:node-fmt "$< port @@%{port-max}$n";
		}

		leaf port-max {
		    type uint16;
		    description
			"The last source port in a range.";
		    ngcliext:sibling-fmt " @@";
		}
	    }

	    case port-table {
		leaf port-table-name {
		    type leafref {
			path "/ngvpf:vpf-config"
			    + "/ngvpf:port-tables"
			    + "/ngvpf:table"
			    + "/ngvpf:name";
		    }
		    ngcliext:node-fmt "$< port-table @@$n";
		}
	    }
	}
    }

    grouping vpf-match-base {
	description
	    "The packet attributes to match in an VPF rule.";

	container from {
	    description
		"The source pattern to match in an VPF rule.";

	    ngcliext:parent-fmt "^from";

	    uses vpf-endpoint;
	}

	container to {
	    description
		"The destination pattern to match in an VPF rule.";

	    ngcliext:parent-fmt "^to";

	    uses vpf-endpoint;
	}

	leaf protocol-set {
	    type ngcom:ip-protocol-name-or-number-set;
	    description
		"A set of IP protocol names or numbers.";
	    ngcliext:node-fmt "^protocol @@$n";
	}

	leaf tcp-flags-mask {
	    type ngcom:tcp-flags;
	    description
		"The TCP flags mask as a set of names.";
	    ngcliext:node-fmt "^tcp flags mask @@$n";
	}

	leaf tcp-flags-value {
	    type ngcom:tcp-flags;
	    description
		"The TCP flags value as a set of flags names.";
	    ngcliext:node-fmt "^tcp flags value @@$n";
	}

	leaf icmp-type {
	    type uint8;
	    description
		"The ICMP type.";
		ngcliext:node-fmt "^icmp type @@$n";
	}

	leaf icmp-code {
	    type uint8;
	    must "../icmp-type" {
		error-message
		    "ICMP code requires ICMP type";
	    }
	    description
		"The ICMP code.";
		ngcliext:node-fmt "^icmp code @@$n";
	}
    }

    grouping vpf-match-config {

	uses vpf-match-base;

	leaf dest-route-table {
	    type leafref {
		path "/ngrttab:route-table-config" +
		     "/ngrttab:static-routes" +
		     "/ngrttab:route-table/ngrttab:name";
	    }
	    description
		"Name of destination VRF for 'in' filter and NAT rules. " +
		"Allows input filter rule flow to match return traffic. " +
		"Allows input NAT rule to direct packets to specific VRF.";
	    ngcliext:node-fmt "^$% @@$n";
	}
    }

    grouping vpf-match-state {

	uses vpf-match-base;

	leaf dest-route-table {
	    type ngcom:rt-identifier-15;
	    description
		"Name of destination VRF for 'in' filter and NAT rules. " +
		"Allows input filter rule flow to match return traffic. " +
		"Allows input NAT rule to direct packets to specific VRF.";
	}
    }

    grouping vpf-match-statistics {
	container match-statistics {
		leaf packets {
		    type uint64;
		    description
			"Amount of packets.";
		}

		leaf bytes {
		    type uint64;
		    description
			"Amount of bytes.";
		}
	}
    }

    container "vpf-config" {
	description
	    "VPP Packet Filter (VPF) data needed to support VPP.
	     It consists of a set of named tables containing IP prefixes,
	     named tables containing ports, a set of named filtering rules,
	     and a set of named NAT rules.";

	ngcliext:parent-fmt "vpf";

	container prefix-tables {
	    description
		"Tables of named IP prefix lists.";

	    ngcliext:parent-fmt "$< prefix-table";
	    ngcliext:post-node-fmt "$n";

	    list table {
		key "name";

		ngcliext:node-fmt "$< @{name}$n";
		ngcliext:pre-children-op "push";

		leaf name {
		    type ngcom:identifier-63;
		    description
			"The name of an IP prefix table.";
		}

		leaf description {
		    type ngcom:description-63;
		    description
			"A text description of the VPF prefix table.";
		    ngcliext:node-fmt "^description @@$n";
		    cl:ignore-compare;
		}

		choice table-type {
		    case inline {
			container prefixes {
			    description
				"A named set of IP prefixes.";

			    list prefix {
				key "ip-prefix";
				ngcliext:post-child-fmt "$n";

				leaf ip-prefix {
				    type inet:ip-prefix;
				    description
					"Either an IPv4 or IPv6 prefix.";
				    ngcliext:node-fmt "^prefix @@";
				}

				leaf description {
				    type ngcom:description-63;
				    description
					"A user description of the VPF
					 prefix table entry.";
				    ngcliext:node-fmt " description @@";
				    cl:ignore-compare;
				}
			    }
			}
		    }

		    case mmdb-file {
			container mmdb-file {
			    ngcliext:post-node-fmt "$n";
			    leaf file {
				type string;
				description
				    "Path to the MMDB file.";
				mandatory true;
				ngcliext:node-fmt "^mmdb $% @@";
			    }

			    leaf field {
				type vpf-select-mmdb-field;
				description
				    "One of 'asn', 'alpha2code', 'region',
				     or 'city'.";
				ngcliext:node-fmt " select @@";
			    }

			    leaf comparison {
				type vpf-select-comparison;
				description
				    "Match comparison operation.
				     eq, ne, lt, le, gt, or ge";
				ngcliext:node-fmt " @@";
			    }

			    choice match-value {
				case match-uint32 {
				    leaf match-uint32 {
					type uint32;
					description
					    "A uint32 that must match.";
					ngcliext:node-fmt " @@";
				    }
				}

				case match-string {
				    leaf match-string {
					type string {
					    length "1..63";
					}
					description
					    "A string that must match.";
					ngcliext:node-fmt " $q@@$q";
				    }
				}
			    }
			}
		    }

		    case csv-file {
			container csv-file {
			    ngcliext:post-node-fmt "$n";
			    leaf file {
				type string;
				description
				    "Path to the CSV file.";
				mandatory true;
				ngcliext:node-fmt "^csv $% @@";
			    }

			    leaf field {
				type vpf-select-csv-field;
				description
				    "One of 'u0' .. 'u9', or 's0' .. 's9'.";
				ngcliext:node-fmt " select @@";
			    }

			    leaf comparison {
				type vpf-select-comparison;
				description
				    "Match comparison operation.
				     eq, ne, lt, le, gt, or ge";
				ngcliext:node-fmt " @@";
			    }

			    choice match-value {
				case match-uint32 {
				    leaf match-uint32 {
					type uint32;
					description
					    "A uint32 that must match.";
					ngcliext:node-fmt " @@";
				    }
				}

				case match-string {
				    leaf match-string {
					type string {
					    length "1..63";
					}
					description
					    "A string that must match.";
					ngcliext:node-fmt " @@";
				    }
				}
			    }
			}
		    }
		}
	    }
	}

	container port-tables {
	    description
		"Tables of named port lists.";

	    ngcliext:parent-fmt "$< port-table";
	    ngcliext:post-node-fmt "$n";

	    list table {
		key "name";

		ngcliext:node-fmt "$< @{name}$n";
		ngcliext:pre-children-op "push";

		leaf name {
		    type ngcom:identifier-63;
		    description
			"The name of a port table.";
		}

		leaf description {
		    type ngcom:description-63;
		    description
			"A text description of the VPF port table.";
		    ngcliext:node-fmt "^description @@$n";
		    cl:ignore-compare;
		}
		
		container ports {
		    description
			"A named set of ports.";

		    list port {
		        description "List of ports";

		        key "port-value";
		        ngcliext:post-child-fmt "$n";

		        leaf port-value {
		            type uint16;
		            description "Port.";
		            ngcliext:node-fmt "^port @@";
		        }

		        leaf description {
		            type ngcom:description-63;
		            description "A user description of the VPF port table entry.";
		            ngcliext:node-fmt " description @@";
		            cl:ignore-compare;
		        }
		    }
		}
	    }
	}

	container filter-rulesets {
	    description
		"A list of named VPF filter rulesets.";

	    ngcliext:parent-fmt "$< filter";
	    ngcliext:post-node-fmt "$n";

	    list ruleset {
		key name;

		ngcliext:node-fmt "$< $% @{name}$n";
		ngcliext:pre-children-op "push";

		leaf name {
		    type ngcom:identifier-63;
		    description
			"The name of the filter ruleset.";
		}

		leaf description {
		    type ngcom:description-63;
		    description
			"A user description of the VPF filter ruleset.";
		    ngcliext:node-fmt "^$% @@$n";
		    cl:ignore-compare;
		}

		container rules {
		    description
			"A list of filter rules within a ruleset
			 ordered by sequence number.";

		    list rule {
			key sequence;

			ngcliext:node-fmt "^$% @{sequence}$n";
			ngcliext:pre-children-op "push";

			leaf sequence {
			    type uint32;
			    description
				"The VPF filter rule sequence number.";
			}

			leaf description {
			    type ngcom:description-63;
			    description
				"A user description of the VPF filter rule.";
			    ngcliext:node-fmt "^$% @@$n";
			    cl:ignore-compare;
			}

			container filter {
			    uses vpf-match-config;

			    must 'not(child::node()/ipv4-prefix and child::node()/ipv6-prefix)' {
				error-message
				    "Address family must be identical for " +
				    "source and destination prefix on " +
				    "filter rules.";
			    }

			}

			leaf ip-version {
			    type ngcom:ip-address-family;
			    description
				"Indicates the IP version (ipv4 or ipv6)
				 applicable to this VPF rule";
			    ngcliext:node-fmt "^$% @@$n";
			}

			leaf pass {
			    type boolean;
			    description
				"If true, the packet is passed, else blocked.";
			    ngcliext:node-op "bool";
			    ngcliext:node-fmt "|^$%$n";
			}

			leaf tentative {
			    type boolean;
			    description
				"If this rule is matched, ruleset examination
				 continues and this rule is applied only if
				 there is no other rule to apply. If there
				 is one, then this rule’s match is ignored
				 and the other rule takes preference.";
			    ngcliext:node-op "bool";
			    ngcliext:node-fmt "|^$%$n";
			}

			leaf stateful {
			    type boolean;
			    description
				"Create a stateful connection entry upon
				 match. On a block rule, creates a stateful
				 block connection that unconditionally drops
				 matching packets while it exists. Block
				 connections support return-rst and return-icmp
				 for subsequent packets.";
			    ngcliext:node-op "bool";
			    ngcliext:node-fmt "|^$%$n";
			}

			leaf vrf-bound {
			    type boolean;
			    description
				"Associate stateful connection entry with " +
				"VRF of outbound interface instead of " +
				"interface index.";
			    must "current() = 'false' or ../stateful = 'true'" {
				error-message
				    "Filter Rule must be stateful to use " +
				    "vrf-bound state";
			    }
			    ngcliext:node-op "bool";
			    ngcliext:node-fmt "|^$%$n";
			}

			leaf return-rst {
			    type boolean;
			    description
				"Return a TCP reset on match.";
			    must "current() = 'false' or not(../pass = 'true')" {
				error-message
				    "Return flags are only supported on block rules";
			    }
			    must "current() = 'false' or ../direction = 'in'" {
				error-message
				    "Return flags are only supported on 'in' rules";
			    }
			    ngcliext:node-op "bool";
			    ngcliext:node-fmt "|^$%$n";
			}

			leaf return-icmp {
			    type boolean;
			    description
				"Return an ICMP error on match (Destination
				 Unreachable/Administratively Prohibited).";
			    must "current() = 'false' or not(../pass = 'true')" {
				error-message
				    "Return flags are only supported on block rules";
			    }
			    must "current() = 'false' or ../direction = 'in'" {
				error-message
				    "Return flags are only supported on 'in' rules";
			    }
			    ngcliext:node-op "bool";
			    ngcliext:node-fmt "|^$%$n";
			}

			leaf direction {
			    type vpf-filter-direction;
			    default out;
			    description
				"One of 'in', 'out'.";
			    ngcliext:node-fmt "^$% @@$n";
			}
		    }
		}
	    }
	}

	container nat-rulesets {
	    description
		"A list of VPF NAT rulesets.";

	    ngcliext:parent-fmt "$< nat";
	    ngcliext:post-node-fmt "$n";

	    list ruleset {
		key name;

		ngcliext:node-fmt "$< $% @{name}$n";
		ngcliext:pre-children-op "push";

		leaf name {
		    type ngcom:identifier-63;
		    description
			"The name of the NAT ruleset.";
		}

		leaf description {
		    type ngcom:description-63;
		    description
			"A user description of the VPF NAT ruleset.";
		    ngcliext:node-fmt "^$% @@$n";
		    cl:ignore-compare;
		}

		container rules {
		    description
			"A list of NAT rules within a ruleset
			 ordered by sequence number.";

		    list rule {
			key sequence;

			ngcliext:node-fmt "^$% @{sequence}$n";
			ngcliext:pre-children-op "push";

			leaf sequence {
			    type uint32;
			    description
				"The VPF NAT rule sequence number.";
			}

			leaf description {
			    type ngcom:description-63;
			    description
				"A user description of the VPF NAT rule.";
			    ngcliext:node-fmt "^$% @@$n";
			    cl:ignore-compare;
			}

			container match {
			    uses vpf-match-config;

			    must 'not(child::node()/ipv4-prefix and child::node()/ipv6-prefix)' {
				error-message
				    "Address family must be identical for " +
				    "source and destination prefix on NAT " +
				    "rules.";
			    }
			}

			leaf dynamic {
			    type boolean;
			    description
				"Dynamic mapping.";
			    ngcliext:node-op "bool";
			    ngcliext:node-fmt "|^$%$n";
			}

			leaf no-port-translation {
			    type boolean;
			    description
				"No port translation.";
			    ngcliext:node-op "bool";
			    ngcliext:node-fmt "|^$%$n";
			}

			leaf algorithm {
			    type vpf-nat-algorithm;
			    description
				"One of one-to-one (default if static), netmap, src ip hash (default if dynamic), ip hash, round robin, or npt66.";
			    ngcliext:node-fmt "^$% @@$n";
			}

			leaf direction {
			    type vpf-nat-direction;
			    description
				"One of 'in' or 'out'.";
			    ngcliext:node-fmt "^$% @@$n";
			}

			container translation {
			    description
				"NAT translation information.";

			    choice translation-port-or-range {
				case translation-port {
				    leaf port {
			    	        type uint16;
			    	        description
			    	            "Port to use for translation.
			    	             0 means no port.";
			    	        ngcliext:node-fmt "^nat-port @@$n";
			    	    }
				}

				case translation-port-range {
				    /*
				     * Wrap min and max in a container so that
				     * these can be atomically removed.
				     * RESTCONF would otherwise struggle,
				     * forcing the user to replace whole
				     * container "translation" instead.
				     */
				    container translation-range {
					leaf port-min {
					    type uint16;
					    description
						"Minimum port to use for translation.
						 0 means no port.";
					    ngcliext:node-fmt "^nat-port-range @@";
					    must "current() = '0' or ../../../dynamic = 'true'" {
						error-message
						    "NAT Rule must be dynamic to use " +
						     "translation port range";
					    }
					}

					leaf port-max {
					    type uint16;
					    description
						"Maximum port to use for translation.
						 0 means no port.";
					    ngcliext:node-fmt " @@$n";
					    must "current() = '0' or ../../../dynamic = 'true'" {
						error-message
						    "NAT Rule must be dynamic to use " +
						    "translation port range";
					    }
					    must ". > ../port-min" {
						error-message
						    "port-max must be greater than port-min";
					    }
					    mandatory true;
					    when "../port-min";
					}
				    }
				}

				case port-mapping {
				    leaf port-range-start {
			    	        type uint16;
			    	        description
			    	            "Minimum port for port-mapping.
			    	             0 means no port.";
			    	        ngcliext:node-fmt "^nat-port-mapping @@$n";
					must "current() = '0' or (../../direction = 'out' and ../../match/from/port-min and ../../match/from/port-max) or (../../direction = 'in' and ../../match/to/port-min and ../../match/to/port-max)" {
					    error-message
						"NAT rule must match the port range it rewrites (match/from for direction out, match/to for direction in) to use port-mapping.";
					}
					must "current() = '0' or (../../direction = 'out' and ../../match/from/port-min and ../../match/from/port-max and ((current() + (../../match/from/port-max - ../../match/from/port-min)) <= 65535)) or (../../direction = 'in' and ../../match/to/port-min and ../../match/to/port-max and ((current() + (../../match/to/port-max - ../../match/to/port-min)) <= 65535))" {
					    error-message
						"port-mapping translation range must not exceed port 65535.";
					}
			    	    }
				}
			    }

			    choice translation-type {
				case interface {
				    leaf if-name {
					type ngcom:if-identifier-63;
					description
					    "Use IF addresses for
					     translation.";
					ngcliext:node-fmt "^nat-interface @@$n";
				    }
				}

				case prefix {
				    leaf prefix {
					 type inet:ip-prefix;
					 description
					     "Translation prefix.";
					ngcliext:node-fmt "^nat-prefix @@$n";
					must "not(../../algorithm='npt66') or "
					     + "number(substring-after(current(), '/'))"
					     + " <= 112" {
					    error-message
						"NAT rule with npt66 algorithm requires a translation prefix of /112 or shorter.";
					}
				    }
				}

				case prefix-table-name {
				    leaf prefix-table-name {
					type leafref {
					    path "/ngvpf:vpf-config/ngvpf:prefix-tables/ngvpf:table/ngvpf:name";
					}
					description
					    "Translation table name.";
					ngcliext:node-fmt "^nat-prefix-table @@$n";
				    }
				}
			    }
			}

			leaf dest-route-table {
			    type leafref {
				path "/ngrttab:route-table-config" +
				     "/ngrttab:static-routes" +
				     "/ngrttab:route-table/ngrttab:name";
			    }
			    description
				"Name of destination VRF for 'in' NAT rule.";
			    ngcliext:node-fmt "^$% @@$n";
			}

			leaf vrf-bound {
			    type boolean;
			    description
				"Associate stateful connection entry with " +
				"VRF of outbound interface instead of " +
				"interface index.";
			    must "current() = 'false' or ../dynamic = 'true'" {
				error-message
				    "NAT Rule must be dynamic to use " +
				    "vrf-bound state";
			    }
			    ngcliext:node-op "bool";
			    ngcliext:node-fmt "|^$%$n";
			}

			leaf endpoint-independent {
			    type boolean;
			    description
				"Create endpoint-independent state.";
			    must "current() = 'false' or
				(../dynamic = 'true' and ../direction = 'out')" {
				error-message
				    "NAT Rule must be dynamic with direction out to use " +
				    "endpoint-independent state";
			    }
			    ngcliext:node-op "bool";
			    ngcliext:node-fmt "|^$%$n";
			}

		    }
		}
	    }
	}

	container options {
	    description
		"VPF interface configuration and enablement options.";

	    ngcliext:node-fmt "$< $%$n";
	    ngcliext:pre-children-op "push";
	    ngcliext:post-node-fmt "$n";

	    container startup {
		description
		    "Startup options.";

		container max-connections-per-thread {
		    description
			"Maximum connections per thread.";

		    ngcliext:parent-fmt "^$^ $%";

		    leaf ip4 {
			type uint32;
			default 131072;
			description
			    "Maximum IPv4 connections per thread.";
			ngcliext:node-fmt "$< $% @@$n";
		    }

		    leaf ip6 {
			type uint32;
			default 32768;
			description
			    "Maximum IPv6 connections per thread.";
			ngcliext:node-fmt "$< $% @@$n";
		    }
		}

		container max-block-connections-per-thread {
		    description
			"Maximum stateful block connections per thread.";

		    ngcliext:parent-fmt "^$^ $%";

		    leaf ip4 {
			type uint32;
			default 0;
			description
			    "Maximum IPv4 stateful block connections per thread. A value of 0 means no block-specific limit.";
			ngcliext:node-fmt "$< $% @@$n";
		    }

		    leaf ip6 {
			type uint32;
			default 0;
			description
			    "Maximum IPv6 stateful block connections per thread. A value of 0 means no block-specific limit.";
			ngcliext:node-fmt "$< $% @@$n";
		    }
		}

		container port-mapping {
		    description
			"Port mapping.";

		    ngcliext:parent-fmt "^$^ $%";

		    leaf min-port {
			type uint16 {
			    range "1024..65535";
			}
			default 1024;
			description
			    "Lowest port used for port mapping.";
			ngcliext:node-fmt "$< $% @@$n";
		    }

		    leaf max-port {
			type uint16 {
			    range "1024..65535";
			}
			must ". >= ../min-port" {
			    error-message
				"max-port value MUST be greater or equal to" +
				 " min-port.";
			}
			default 49151;
			description
			    "Highest port used for port mapping.";
			ngcliext:node-fmt "$< $% @@$n";
		    }
		}
	    }

	    container runtime {
		description
		    "Runtime options.";

		container drop-options {
		    description
			"Drop packets having IP options.";

		    ngcliext:parent-fmt "^$^ $%";

		    leaf ip4 {
			type boolean;
			default false;
			description
			    "Drop IPv4 packets having IP options.";
			ngcliext:node-fmt "$< $% @@$n";
		    }

		    leaf ip6 {
			type boolean;
			default false;
			description
			    "Drop IPv6 packets having IP options.";
			ngcliext:node-fmt "$< $% @@$n";
		    }
		}

		container timeouts {
		    description
			"Timeouts.";

		    ngcliext:parent-fmt "^$^ $%";

		    container generic {
			description
			    "Generic timeouts.";

			ngcliext:parent-fmt "$< $%";

						leaf new {
			    type uint32 {
			    	range "1..max";
			    }
			    units "seconds";
			    default 30;
			    description
				"New state.";
			    ngcliext:node-fmt "$< $% @@$n";
			}

			leaf established {
			    type uint32 {
			    	range "1..max";
			    }
			    units "seconds";
			    default 60;
			    description
				"Established state.";
			    ngcliext:node-fmt "$< $% @@$n";
			}
		    }

		    container tcp {
			description
			    "TCP timeouts.";

			ngcliext:parent-fmt "$< $%";

			leaf closed {
			    type uint32 {
			    	range "1..max";
			    }
			    units "seconds";
			    default 10;
			    description
				"Closed state.";
			    ngcliext:node-fmt "$< $% @@$n";
			}

			leaf new {
			    type uint32 {
			    	range "1..max";
			    }
			    units "seconds";
			    default 30;
			    description
				"New state.";
			    ngcliext:node-fmt "$< $% @@$n";
			}

			leaf established {
			    type uint32 {
			    	range "1..max";
			    }
			    units "seconds";
			    default 86400;
			    description
				"Established state.";
			    ngcliext:node-fmt "$< $% @@$n";
			}

			leaf half-closed {
			    type uint32 {
			    	range "1..max";
			    }
			    units "seconds";
			    default 21600;
			    description
				"Half-closed state.";
			    ngcliext:node-fmt "$< $% @@$n";
			}

			leaf closing {
			    type uint32 {
			    	range "1..max";
			    }
			    units "seconds";
			    default 900;
			    description
				"Closing and Last-Ack states.";
			    ngcliext:node-fmt "$< $% @@$n";
			}

			leaf time-wait {
			    type uint32 {
			    	range "1..max";
			    }
			    units "seconds";
			    default 240;
			    description
				"Time-wait state.";
			    ngcliext:node-fmt "$< $% @@$n";
			}
		    }

		    container block {
			description
			    "Stateful block connection timeout.";

			ngcliext:parent-fmt "$< $%";

			leaf timeout {
			    type uint32 {
			    	range "1..max";
			    }
			    units "seconds";
			    default 60;
			    description
				"Stateful block connection timeout.";
			    ngcliext:node-fmt "$< $% @@$n";
			}
		    }
		}

		container tcp {
		    description
			"TCP.";

		    ngcliext:parent-fmt "^$^ $%";

		    leaf strict-rst-order {
			type boolean;
			default true;
			description
			    "Enforce strict TCP RST order.";
			ngcliext:node-fmt "$< $% @@$n";
		    }

		    leaf max-ack-win {
			type uint32;
			default 66000;
			description
			    "Maximum TCP ACK window.";
			ngcliext:node-fmt "$< $% @@$n";
		    }
		}

		container expired-connection-cleanup {
		    ngcliext:parent-fmt "^$^ $%";

		    description
			"Limit on number of expired connections freed before VPF processes a frame of packets.";

		    leaf generic-limit {
			type uint32;
			default 256;
			description
			    "Maximum number of generic connections freed before VPF processes a frame of packets.";
			ngcliext:node-fmt "$< $% @@$n";
		    }

		    leaf tcp-limit {
			type uint32;
			default 256;
			description
			    "Maximum number of TCP connections freed before VPF processes a frame of packets.";
			ngcliext:node-fmt "$< $% @@$n";
		    }

		    leaf block-limit {
			type uint32;
			default 256;
			description
			    "Maximum number of block connections freed before VPF processes a frame of packets.";
			ngcliext:node-fmt "$< $% @@$n";
		    }
		}
	    }

	    container interfaces {
		description
		    "The names of filtering and NAT rulesets applied
		     to interfaces.";

		list interface {
		    key "if-name";

		    ngcliext:parent-fmt "^$% @{if-name}";

		    leaf if-name {
			type ngcom:if-identifier-63;
			description
			    "The name of an interface.";
		    }

		    leaf filter-ruleset {
			type leafref {
			    path "/ngvpf:vpf-config"
				+ "/ngvpf:filter-rulesets"
				+ "/ngvpf:ruleset"
				+ "/ngvpf:name";
			}
			description
			    "The name of the filter ruleset on this
			     interface.";
			ngcliext:node-fmt "$< $% @@$n";
		    }

		    leaf filter-ruleset-post-nat {
			type leafref {
			    path "/ngvpf:vpf-config"
				+ "/ngvpf:filter-rulesets"
				+ "/ngvpf:ruleset"
				+ "/ngvpf:name";
			}
			description
			    "The name of the post-NAT filter ruleset on this
			     interface.";
			ngcliext:node-fmt "$< $% @@$n";
		    }

		    leaf nat-ruleset {
			type leafref {
			    path "/ngvpf:vpf-config"
				+ "/ngvpf:nat-rulesets"
				+ "/ngvpf:ruleset"
				+ "/ngvpf:name";
			}
			description
			    "The name of the NAT ruleset on this interface.";
			ngcliext:node-fmt "$< $% @@$n";
		    }
		}
	    }
	}

	container ipfix {
	    description
		"IPFIX exporting options.";

	    ngcliext:node-fmt "$< $%$n";
	    ngcliext:pre-children-op "push";

	    leaf enable {
		type empty;
		description
		    "If present, IPFIX exporting is enabled.";
		ngcliext:node-fmt "^$%$n";
	    }

	    leaf domain {
		type uint32;
		default 1;
		description
		    "Domain ID.";
		ngcliext:node-fmt "^$% @@$n";
	    }

	    leaf src-port {
		type uint16;
		default 4739;
		description
		    "Source port number.";
		ngcliext:node-fmt "^$% @@$n";
	    }
	}

        container ha {
            description
                "High-availability options.";

	    ngcliext:node-fmt "$< $%$n";
	    ngcliext:pre-children-op "push";

            list importer {
                key "local-address local-port remote-address remote-port";

	        ngcliext:node-fmt "^$%";

                leaf local-address {
                    type inet:ip-address;
                    description
                        "Local IP address.";
	            ngcliext:node-fmt " $% @@";
                }

                leaf local-port {
                    type uint16;
                    description
                        "Local port number.";
	            ngcliext:node-fmt " $% @@";
                }

                leaf remote-address {
                    type inet:ip-address;
                    description
                        "Remote IP address.";
	            ngcliext:node-fmt " $% @@";
                }

                leaf remote-port {
                    type uint16;
                    description
                        "Remote port number.";
	            ngcliext:node-fmt " $% @@$n";
                }
            }

            list exporter {
                key "local-address local-port remote-address remote-port";

	        ngcliext:node-fmt "^$%";

                leaf local-address {
                    type inet:ip-address;
                    description
                        "Local IP address.";
	            ngcliext:node-fmt " $% @@";
                }

                leaf local-port {
                    type uint16;
                    description
                        "Local port number.";
	            ngcliext:node-fmt " $% @@";
                }

                leaf remote-address {
                    type inet:ip-address;
                    description
                        "Remote IP address.";
	            ngcliext:node-fmt " $% @@";
                }

                leaf remote-port {
                    type uint16;
                    description
                        "Remote port number.";
	            ngcliext:node-fmt " $% @@";
                }

                leaf mtu {
                    type uint16 {
                        range "1280..2048";
                    }

                    mandatory true;
                    description
                        "MTU.";
	            ngcliext:node-fmt " $% @@$n";
                }
            }
        }

	leaf enable {
	    type empty;
	    description
		"If present, the feature is enabled.";
	    ngcliext:node-fmt "$< $%$n";
	}
    }


    container "vpf-state" {
	config "false";

	description
	    "Netbsd Packet Filter (VPF) state data. It consists of a set of
	     named tables containing IP prefixes, a set of named filtering
	     rules, a set of named NAT rules, and params.";

	container prefix-tables {
	    description
		"Tables of named IP prefix lists.";

	    list table {
		key "name";

		leaf name {
		    type ngcom:identifier-63;
		    description
			"The name of an IP prefix table.";
		}

		leaf description {
		    type ngcom:description-63;
		    description
			"A text description of the VPF prefix table.";
		}

		container hash-buckets {
		    description
			"Hash buckets.";

		    leaf ip4 {
			type uint32;
			description
			    "IPv4 hash buckets.";
		    }

		    leaf ip6 {
			type uint32;
			description
			    "IPv6 hash buckets.";
		    }
		}

		container prefixes {
		    description
			"Each table is a named set of IP prefixes.";

		    list prefix {
			key "ip-prefix";
			description
			    "A named set of IPv4 and IPv6 prefixes.";

			leaf ip-prefix {
				type inet:ip-prefix;
				description
				    "Either an IPv4 or IPv6 prefix.";
			}

			leaf description {
			    type ngcom:description-63;
			    description
				"A user description of the VPF prefix table entry.";
			}
		    }
		}
	    }
	}

	container port-tables {
	    description
		"Tables of named port lists.";

	    list table {
		key "name";

		leaf name {
		    type ngcom:identifier-63;
		    description
			"The name of a port table.";
		}

		leaf description {
		    type ngcom:description-63;
		    description
			"A text description of the VPF port table.";
		}
		
		container ports {
		    description
			"A named set of ports.";

		    list port {
		        description "List of ports";

		        key "port-value";

		        leaf port-value {
		            type uint16;
		            description "Port.";
		        }

		        leaf description {
		            type ngcom:description-63;
		            description "A user description of the VPF port table entry.";
		        }
		    }
		}
	    }
	}

	container filter-rulesets {
	    description
		"A list of named VPF filter rulesets.";

	    list ruleset {
		key name;

		leaf name {
		    type ngcom:identifier-63;
		    description
			"The name of the filter ruleset.";
		}

		leaf description {
		    type ngcom:description-63;
		    description
			"A user description of the VPF filter ruleset.";
		}

		container rules {
		    description
			"A list of filter rules within a ruleset
			 ordered by sequence number.";

		    list rule {
			key sequence;

			leaf sequence {
			    type uint32;
			    description
				"The VPF filter rule sequence number.";
			}

			leaf description {
			    type ngcom:description-63;
			    description
				"A user description of the VPF filter rule.";
			}

			container filter {
			    uses vpf-match-state;
			}

			leaf ip-version {
			    type ngcom:ip-address-family;
			    description
				"Indicates the IP version (ipv4 or ipv6)
				 applicable to this VPF rule";
			}

			leaf pass {
			    type boolean;
			    description
				"If true, the packet is passed, else blocked.";
			}

			leaf tentative {
			    type boolean;
			    description
				"If this rule is matched, ruleset examination
				 continues and this rule is applied only if
				 there is no other rule to apply. If there
				 is one, then this rule’s match is ignored
				 and the other rule takes preference.";
			}

			leaf stateful {
			    type boolean;
			    description
				"Create a stateful connection entry upon
				 match.";
			}

			leaf vrf-bound {
			    type boolean;
			    description
				"Associate stateful connection entry with " +
				"VRF of outbound interface instead of " +
				"interface index.";
			}

			leaf return-rst {
			    type boolean;
			    description
				"Return a TCP reset on match.";
			}

			leaf return-icmp {
			    type boolean;
			    description
				"Return an ICMP error on match (Destination
				 Unreachable/Administratively Prohibited).";
			}

			leaf direction {
			    type vpf-filter-direction;
			    description
				"One of 'in', 'out'.";
			}

			leaf dest-route-table {
			    type ngcom:rt-identifier-15;
			    description
				"Name of destination VRF for 'in' filter " +
				"rule.";
			}

			uses vpf-match-statistics;
		    }
		}
	    }
	}

	container nat-rulesets {
	    description
		"A list of VPF NAT rulesets.";

	    list ruleset {
		key name;

		leaf name {
		    type ngcom:identifier-63;
		    description
			"The name of the NAT ruleset.";
		}

		leaf description {
		    type ngcom:description-63;
		    description
			"A user description of the VPF NAT ruleset.";
		}

		container rules {
		    description
			"A list of NAT rules within a ruleset
			 ordered by sequence number.";

		    list rule {
			key sequence;

			leaf sequence {
			    type uint32;
			    description
				"The VPF NAT rule sequence number.";
			}

			leaf description {
			    type ngcom:description-63;
			    description
				"A user description of the VPF NAT rule.";
			}

			container match {
			    uses vpf-match-state;
			}

			leaf dynamic {
			    type boolean;
			    description
				"Dynamic mapping.";
			}

			leaf no-port-translation {
			    type boolean;
			    description
				"No port translation.";
			}

			leaf algorithm {
			    type vpf-nat-algorithm;
			    description
				"One of one-to-one, netmap, src ip hash, ip hash, round robin, or npt66.";
			}

			leaf direction {
			    type vpf-nat-direction;
			    description
				"One of 'in' or 'out'.";
			}

			container translation {
			    description
				"NAT translation information.";

			    choice translation-port-or-range {
				case translation-port {
				    leaf port {
			    	        type uint16;
			    	        description
			    	            "Port to use for translation.
			    	             0 means no port.";
			    	    }
				}

				case translation-port-range {
				    container translation-range {
					leaf port-min {
					    type uint16;
					    description
						"Minimum port to use for translation.
						 0 means no port.";
					}

					leaf port-max {
					    type uint16;
					    description
						"Maximum port to use for translation.
						 0 means no port.";
					}
				    }
				}

				case port-mapping {
				    leaf port-range-start {
			    	        type uint16;
			    	        description
			    	            "Minimum port for port-mapping.
			    	             0 means no port.";
			    	    }
				}
			    }

			    choice translation-type {
				case interface {
				    leaf if-name {
					type ngcom:if-identifier-63;
					description
					    "Use IF addresses for
					     translation.";
				    }
				}

				case prefix-table-name {
				    leaf prefix-table-name {
					type ngcom:if-identifier-63;
					description
					    "Use Table name for
					     translation.";
				    }
				}

				case prefix {
				    leaf prefix {
					 type inet:ip-prefix;
					 description
					     "Translation prefix.";
				    }
				}
			    }
			}

			leaf dest-route-table {
			    type ngcom:rt-identifier-15;
			    description
				"Name of destination VRF for 'in' NAT rule.";
			}

			leaf vrf-bound {
			    type boolean;
			    description
				"Associate stateful connection entry with " +
				"VRF of outbound interface instead of " +
				"interface index.";
			}

			leaf endpoint-independent {
			    type boolean;
			    description
				"Create endpoint-independent state.";
			}

			uses vpf-match-statistics;
		    }
		}
	    }
	}

	container options {
	    description
		"VPF interface state and enablement options.";

	    container startup {
		description
		    "Startup options.";

		container max-connections-per-thread {
		    description
			"Maximum connections per thread.";

		    leaf ip4 {
			type uint32;
			description
			    "Maximum IPv4 connections per thread.";
		    }

		    leaf ip6 {
			type uint32;
			description
			    "Maximum IPv6 connections per thread.";
		    }
		}

		container max-block-connections-per-thread {
		    description
			"Maximum stateful block connections per thread.";

		    leaf ip4 {
			type uint32;
			description
			    "Maximum IPv4 stateful block connections per thread.";
		    }

		    leaf ip6 {
			type uint32;
			description
			    "Maximum IPv6 stateful block connections per thread.";
		    }
		}

		container port-mapping {
		    description
			"Port mapping.";

		    leaf min-port {
			type uint16;
			description
			    "Lowest port used for port mapping.";
		    }

		    leaf max-port {
			type uint16;
			description
			    "Highest port used for port mapping.";
		    }
		}
	    }

	    container runtime {
		description
		    "Runtime options.";

		container drop-options {
		    description
			"Drop packets having IP options.";

		    leaf ip4 {
			type boolean;
			description
			    "Drop IPv4 packets having IP options.";
		    }

		    leaf ip6 {
			type boolean;
			description
			    "Drop IPv6 packets having IP options.";
		    }
		}

		container timeouts {
		    description
			"Timeouts.";

		    container generic {
			description
			    "Generic timeouts.";

			leaf new {
			    type uint32;
			    units "seconds";
			    description
				"New state.";
			}

			leaf established {
			    type uint32;
			    units "seconds";
			    description
				"Established state.";
			}
		    }

		    container tcp {
			description
			    "TCP timeouts.";

			leaf closed {
			    type uint32;
			    units "seconds";
			    description
				"Closed state.";
			}

			leaf new {
			    type uint32;
			    units "seconds";
			    description
				"New state.";
			}

			leaf established {
			    type uint32;
			    units "seconds";
			    description
				"Established state.";
			}

			leaf half-closed {
			    type uint32;
			    units "seconds";
			    description
				"Half-closed state.";
			}

			leaf closing {
			    type uint32;
			    units "seconds";
			    description
				"Closing and Last-Ack states.";
			}

			leaf time-wait {
			    type uint32;
			    units "seconds";
			    description
				"Time-wait state.";
			}
		    }

		    container block {
			description
			    "Stateful block connection timeout.";

			leaf timeout {
			    type uint32;
			    units "seconds";
			    description
				"Stateful block connection timeout.";
			}
		    }
		}

		container tcp {
		    description
			"TCP.";

		    leaf strict-rst-order {
			type boolean;
			description
			    "Enforce strict TCP RST order.";
		    }

		    leaf max-ack-win {
			type uint32;
			description
			    "Maximum TCP ACK window.";
		    }
		}

                container expired-connection-cleanup {
                    description
                        "Limit on number of expired connections freed before processing a frame of packets by VPF.";

                    leaf generic-limit {
                        type uint32;
                        description
                            "Maximum number of generic connections freed before processing a frame of packets by VPF.";
                    }

                    leaf tcp-limit {
                        type uint32;
                        description
                            "Maximum number of TCP connections freed before processing a frame of packets by VPF.";
                    }

                    leaf block-limit {
                        type uint32;
                        description
                            "Maximum number of block connections freed before processing a frame of packets by VPF.";
                    }
                }
	    }

	    container interfaces {
		description
		    "The names of filtering and NAT rulesets applied
		     to interfaces.";

		list interface {
		    key "if-name";

		    leaf if-name {
			type ngcom:if-identifier-63;
			description
			    "The name of an interface.";
		    }

		    leaf filter-ruleset {
			type ngcom:identifier-63;
			description
			    "The name of the filter ruleset on this
			     interface.";
		    }

		    leaf filter-ruleset-post-nat {
			type ngcom:identifier-63;
			description
			    "The name of the post-NAT filter ruleset on this
			     interface.";
		    }

		    leaf nat-ruleset {
			type ngcom:identifier-63;
			description
			    "The name of the NAT ruleset on this interface.";
		    }
		}
	    }
	}

	container ipfix {
	    description
		"IPFIX exporting options.";

	    leaf enable {
		type boolean;
		description
		    "Indicates whether IPFIX exporting is enabled.";
	    }

	    leaf domain {
		type uint32;
		description
		    "Domain ID.";
	    }

	    leaf src-port {
		type uint16;
		description
		    "Source port number.";
	    }
	}

        container ha {
            description
                "High-availability options.";

            list importer {
                key "local-address local-port remote-address remote-port";

                leaf local-address {
                    type inet:ip-address;
                    description
                        "Local IP address.";
                }

                leaf local-port {
                    type uint16;
                    description
                        "Local port number.";
                }

                leaf remote-address {
                    type inet:ip-address;
                    description
                        "Remote IP address.";
                }

                leaf remote-port {
                    type uint16;
                    description
                        "Remote port number.";
                }

		leaf last-sent-ago {
		    type decimal64 {
			fraction-digits 2;
		    }

		    description
			"Time since last packet sent to peer.";
		}

		leaf last-heard-ago {
		    type decimal64 {
			fraction-digits 2;
		    }

		    description
			"Time since last packet received from peer.";
		}
            }

            list exporter {
                key "local-address local-port remote-address remote-port";

                leaf local-address {
                    type inet:ip-address;
                    description
                        "Local IP address.";
                }

                leaf local-port {
                    type uint16;
                    description
                        "Local port number.";
                }

                leaf remote-address {
                    type inet:ip-address;
                    description
                        "Remote IP address.";
                }

                leaf remote-port {
                    type uint16;
                    description
                        "Remote port number.";
                }

                leaf mtu {
                    type uint16;
                    description
                        "MTU.";
                }

		leaf last-sent-ago {
		    type decimal64 {
			fraction-digits 2;
		    }

		    description
			"Time since last packet sent to peer.";
		}

		leaf last-heard-ago {
		    type decimal64 {
			fraction-digits 2;
		    }

		    description
			"Time since last packet received from peer.";
		}

		leaf last-heartbeat-uptime {
		    type uint32;
		    description
			"Last uptime value received in heartbeat packet.";
		}
            }
        }

	leaf enable {
	    type boolean;
	    description
		"Indicates whether the feature is enabled.";
	}
    }
}
