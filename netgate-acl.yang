module netgate-acl {

    yang-version 1.1;

    namespace "urn:netgate:xml:yang:netgate-acl";
    prefix "ngacl";

    import ietf-inet-types {
	prefix "inet";
    }

    import netgate-cli-extensions {
	prefix "ngcliext";
    }

    import netgate-common {
	prefix "ngcom";
    }

    organization "Netgate";

    contact "Web: <http://www.netgate.com>";

    description
	"This YANG module provides a Netgate-defined data-model
	 for Access Control Lists.

	 Copyright 2017-2020 Rubicon Communications, LLC.
	 ";

    revision 2023-11-01 {
        description
	    "TNSR Release 23.11.";
    }

    revision 2022-02-15 {
	description
	    "TNSR Release 22.02.";
    }

    revision 2021-02-15 {
	description
	    "TNSR Release 21.02.";
    }

    revision 2020-06-15 {
	description
	    "TNSR Release 20.06.";
    }
    revision 2020-02-15 {
	description
	    "TNSR Release 20.02.";
    }

    revision 2019-08-30 {
	description
	    "TNSR Release 19.08.";
    }

    revision 2019-05-30 {
	description
	    "TNSR Release 19.05.";
    }

    revision 2019-02-15 {
	description
	    "TNSR Release 19.02.";
    }

    revision 2017-05-10 {
	description
	    "Initial revision.";
    }

    typedef acl-protocol-name {
	type enumeration {
	    enum any {
		value 0;
		description "any protocol";
	    }
	    enum tcp {
		value 6;
		description "TCP";
	    }
	    enum udp {
		value 17;
		description "UDP";
	    }
	    enum icmp {
		value 1;
		description "ICMP";
	    }
	    enum icmpv6 {
		value 58;
		description "ICMPv6";
	    }
	}
    }

    typedef acl-protocol-number {
	type uint8;
	description "ip protocol number";
    }

    typedef acl-protocol {
	type union {
	    type acl-protocol-name;
	    type acl-protocol-number;
	}
    }

    typedef acl-rule-action {
	type enumeration {
	    enum deny {
		description
		    "Deny";
	    }
	    enum permit {
		description
		    "Permit";
	    }
	    enum reflect {
		description
		    "Reflect";
	    }
	}
    }

    container "acl-config" {
	description
	    "Access Control Lists (ACL) data needed to support VPP.";

	container acl-table {
	    description
		"Table of ACL lists, indexed by name.  Each entry
		 contains a set of ACL Rules ordered by sequence number.";

	    list acl-list {
		key "acl-name";
		description
		    "ACL list name.";

		ngcliext:node-fmt "acl @{acl-name}$n";
		ngcliext:pre-children-op "push";

		leaf acl-name {
		    type string;
		    mandatory true;
		    description
			"The ACL name as supplied by the developer.
			 It is a unique name used to identify this
			 set of ACL Rules.";
		}

		leaf acl-description {
		    type ngcom:description-63;
		    description
		        "A text description for the ACL.";
		    ngcliext:node-fmt "^description @@$n";
		}

		container acl-rules {
		    description
			"ACL Rule Table ordered by sequence number.";

		    list acl-rule {
			key "sequence";
			description
			    "A List of ACL Rules.";

			ngcliext:node-fmt "^rule @{sequence}$n";
			ngcliext:pre-children-op "push";

			leaf sequence {
			    type uint32;
			    description
				"Rules are executed in increasing sequence
				 number.";
			}

			leaf acl-rule-description {
			    type ngcom:description-63;
			    description
			        "A text description for the ACL rule.";
			    ngcliext:node-fmt "^description @@$n";
			}

			leaf action {
			    type acl-rule-action;
			    mandatory true;
			    description
				"One of the actions 'deny', 'permit', or
				 'reflect'.";
			    ngcliext:node-fmt "^$% @@$n";
			}

			leaf ip-version {
			    type inet:ip-version;
			    mandatory true;
			    description
				"indicates the IP version (ipv4 or ipv6)
			         applicable to this ACL rule";
			    ngcliext:node-fmt "^$% @@$n";
			}

			leaf src-ip-prefix {
			    type inet:ip-prefix;
			    description
				"IP source prefix.";
			    ngcliext:node-fmt "^source address @@$n";
			}

			leaf src-first-port {
			    type uint16;
			    description
				"The first source port in a range.";
				ngcliext:node-fmt "^source port @@%{src-last-port}$n";
			}

			leaf src-last-port {
			    type uint16;
			    description
				"The last source port in a range.";
			    ngcliext:sibling-fmt " @@";
			}

			leaf dst-ip-prefix {
			    type inet:ip-prefix;
			    description
				"IP destination prefix.";
			    ngcliext:node-fmt "^destination address @@$n";
			}

			leaf dst-first-port {
			    type uint16;
			    description
				"The first destination port in a range.";
				ngcliext:node-fmt "^destination port @@%{dst-last-port}$n";
			}

			leaf dst-last-port {
			    type uint16;
			    description
				"The last destination port in a range.";
			    ngcliext:sibling-fmt " @@";
			}

			leaf protocol {
			    type acl-protocol;
			    description
				"IP protocol";
			    ngcliext:node-fmt "^$% @@$n";
			}

			leaf icmp-first-type {
			    type uint8;
			    description
				"The first ICMP type in a range.";
				ngcliext:node-fmt "^icmp type @@%{icmp-last-type}$n";
			}

			leaf icmp-last-type {
			    type uint8;
			    description
				"The last ICMP type in a range.";
			    ngcliext:node-op "prune";
			    ngcliext:sibling-fmt " - @@";
			}

			leaf icmp-first-code {
			    type uint8;
			    description
				"The first ICMP code in a range.";
				ngcliext:node-fmt "^icmp code @@%{icmp-last-code}$n";
			}

			leaf icmp-last-code {
			    type uint8;
			    description
				"The last ICMP code in a range.";
			    ngcliext:node-op "prune";
			    ngcliext:sibling-fmt " - @@";
			}

			leaf tcp-flags-mask {
			    type uint8;
			    description
				"The TCP flags mask.";
				ngcliext:node-fmt "^tcp flags mask @@ %{tcp-flags-value}$n";
			}

			leaf tcp-flags-value {
			    type uint8;
			    description
				"The TCP flags value.";
			    ngcliext:node-op "prune";
			    ngcliext:sibling-fmt "value @@";
			}
		    }
		}
	    }
	}
    }

    container "acl-state" {
	config "false";

	description
	    "Access Control Lists (ACL) state data.";

	container acl-table {
	    description
		"Table of ACL lists, indexed by name.  Each entry
		 contains a set of ACL Rules ordered by sequence number.";

	    list acl-list {
		key "acl-name";
		description
		    "ACL list name.";

		leaf acl-name {
		    type string;
		    mandatory true;
		    description
			"The ACL name as supplied by the developer.
			 It is a unique name used to identify this
			 set of ACL Rules.";
		}

		leaf acl-description {
		    type ngcom:description-63;
		    description
		        "A text description for the ACL.";
		}

		container acl-rules {
		    description
			"ACL Rule Table ordered by sequence number.";

		    list acl-rule {
			key "sequence";
			description
			    "A List of ACL Rules.";

			leaf sequence {
			    type uint32;
			    description
				"Rules are executed in increasing sequence
				 number.";
			}

			leaf acl-rule-description {
			    type ngcom:description-63;
			    description
			        "A text description for the ACL rule.";
			}

			leaf action {
			    type acl-rule-action;
			    description
				"One of the actions 'deny', 'permit', or
				 'reflect'.";
			}

			leaf ip-version {
			    type inet:ip-version;
			    description
				"indicates the IP version (ipv4 or ipv6)
			         applicable to this ACL rule";
			}

			leaf src-ip-prefix {
			    type inet:ip-prefix;
			    description
				"The IPv4 or IPv6 source prefix.";
			}

			leaf src-first-port {
			    type uint16;
			    description
				"The first source port in a range.";
			}

			leaf src-last-port {
			    type uint16;
			    description
				"The last source port in a range.";
			}


			leaf dst-ip-prefix {
			    type inet:ip-prefix;
			    description
				"The IPv4 or IPv6 destination prefix.";
			}

			leaf dst-first-port {
			    type uint16;
			    description
				"The first destination port in a range.";
			}

			leaf dst-last-port {
			    type uint16;
			    description
				"The last destination port in a range.";
			}

			leaf protocol {
			    type acl-protocol;
			    description
				"One of the L4 protocol strings 'tcp', 'udp'
				 or 'icmp'.";
			}

			leaf icmp-first-type {
			    type uint8;
			    description
				"The first ICMP type in a range.";
			}

			leaf icmp-last-type {
			    type uint8;
			    description
				"The last ICMP type in a range.";
			}

			leaf icmp-first-code {
			    type uint8;
			    description
				"The first ICMP code in a range.";
			}

			leaf icmp-last-code {
			    type uint8;
			    description
				"The last ICMP code in a range.";
			}

			leaf tcp-flags-mask {
			    type uint8;
			    description
				"The TCP flags mask.";
			}

			leaf tcp-flags-value {
			    type uint8;
			    description
				"The TCP flags value.";
			}
		    }
		}
	    }
	}
    }
}
