module netgate-ip {

    yang-version 1.1;

    namespace "urn:netgate:xml:yang:netgate-ip";
    prefix "ngip";

    import netgate-cli-extensions {
	prefix "ngcliext";
    }

    organization "Netgate";

    contact "Web: <http://www.netgate.com>";

    description
	"This YANG module provides global ip configuration such
	 as ip-reassembly.

	 Copyright 2019-2020 Rubicon Communications, LLC.
	 ";

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-12-15 {
	description
	    "TNSR Release 19.12.";
    }

    revision 2019-08-30 {
	description
	    "TNSR Release 19.08.";
    }

    grouping reassembly-grouping {
	container ipv4 {
	    description
		"Ip4-reassembly settings.";

	    ngcliext:parent-fmt "$< ipv4";

	    leaf timeout-ms {
		type uint32 {
		    range "1..2000";
		}
		description
		    "Reassembly timeout in milliseconds.";
		ngcliext:node-fmt "$< timeout @@$n";
	    }

	    leaf expire-walk-interval-ms {
		type uint32 {
		    range "1..60000";
		}
		description
		    "Timeout trying to keep fragments.";
		ngcliext:node-fmt "$< expire-walk-interval @@$n";
	    }

	    leaf max-reassemblies {
		type uint32 {
		    range "1..1024";
		}
		description
		    "Maximum reassemblies count.";
		ngcliext:node-fmt "$< $% @@$n";
	    }

	    leaf max-reassembly-length {
		type uint32 {
		    range "1..64";
		}
		description
		    "Maximum reassembly length.";
		ngcliext:node-fmt "$< $% @@$n";
	    }
	}

	container ipv6 {
	    description
		"Ip6-reassembly settings.";

	    ngcliext:parent-fmt "$< ipv6";

	    leaf timeout-ms {
		type uint32 {
		    range "1..2000";
		}
		description
		    "Reassembly timeout in milliseconds.";
		ngcliext:node-fmt "$< timeout @@$n";
	    }

	    leaf expire-walk-interval-ms {
		type uint32 {
		    range "1..60000";
		}
		description
		    "Timeout trying to keep fragments.";
		ngcliext:node-fmt "$< expire-walk-interval @@$n";
	    }

	    leaf max-reassemblies {
		type uint32 {
		    range "1..1024";
		}
		description
		    "Maximum reassemblies count.";
		ngcliext:node-fmt "$< $% @@$n";
	    }

	    leaf max-reassembly-length {
		type uint32 {
		    range "1..64";
		}
		description
		    "Maximum reassembly length.";
		ngcliext:node-fmt "$< $% @@$n";
	    }
	}
    }

    container ip-config {

	description
	    "Internet Protocol (IP) reassembly configuration.";

	ngcliext:parent-fmt "ip";

	container reassembly {
	    ngcliext:parent-fmt "$< $%";

	    container full {
		ngcliext:parent-fmt "$< $%";
		uses reassembly-grouping;
	    }

	    container virtual {
		ngcliext:parent-fmt "$< $%";
		uses reassembly-grouping;
	    }
	}
    }

    container ip-state {
        config false;

	container reassembly {
	    container full {
		uses reassembly-grouping;
	    }

	    container virtual {
		uses reassembly-grouping;
	    }
	}
    }
}
