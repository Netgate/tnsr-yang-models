module netgate-gre {

    yang-version 1.1;

    namespace "urn:netgate:xml:yang:netgate-gre";
    prefix "nggre";

    import ietf-inet-types {
	prefix "inet";
    }

    import netgate-cli-extensions {
	prefix "ngcliext";
    }

    import netgate-common {
	prefix "ngcom";
    }

    organization "Netgate";

    contact "Web: <http://www.netgate.com>";

    description
	"This YANG module provides a Netgate-defined data-model
	 for GRE data.

	 Copyright 2018-2020 Rubicon Communications, LLC.
	 ";

    revision 2021-06-15 {
	description
	    "TNSR Release 21.07.";
    }

    revision 2021-02-15 {
	description
	    "TNSR Release 21.02.";
    }

    revision 2020-06-15 {
	description
	    "TNSR Release 20.06.";
    }

    revision 2020-02-15 {
	description
	    "TNSR Release 20.02.";
    }

    revision 2019-02-15 {
	description
	    "TNSR Release 19.02.";
    }

    revision 2018-02-14 {
	description
	    "Initial revision.";
    }

    typedef gre-tunnel-type{
	type enumeration {
	    enum l3 {
		description
		    "L3";
	    }
	    enum teb {
		description
		    "TEB";
	    }
	    enum erspan {
		description
		    "ERSPN";
	    }
	}
    }

    container "gre-config" {
	description
	    "Configuration for GRE tunnels.";

	container gre-table {
	    description
		"GRE table.";

	    list tunnel {
		key "name";
		unique "instance";

		description
		    "GRE tunnel configuration.";

		ngcliext:node-fmt "gre @{name}$n";
		ngcliext:pre-children-op "push";

		leaf name {
		    type string;
		    description
			"The GRE tunnel identifier.  A unique name
			 for this GRE tunnel.";
		}

		leaf dst-ip-address {
		    type inet:ip-address-no-zone;
		    mandatory true;
		    description
			"The destination IP address.";
		    ngcliext:node-fmt "^destination @@$n";
		}

		leaf erspan-session-id {
		    type uint32 {
			range "0..1023";
		    }
		    description
			"VNI value, u24.";
		    ngcliext:sibling-fmt " session-id @@";
		}

		leaf instance {
		    type uint32;
		    mandatory true;
		    description
			"Each GRE tunnel creates an interface.  The
			 created interface will be named 'gre<X>',
			 where the <X> is the instance number.
			 The instance number must be unique across
			 all GRE entries.";
		    ngcliext:node-fmt "^$% @@$n";
		}

		leaf encap-route-table {
		    type ngcom:rt-identifier-63;
		    description
			"Encapsulation route table name.";
		    ngcliext:node-fmt "^encapsulation route-table @@$n";
		}

		leaf src-ip-address {
		    type inet:ip-address-no-zone;
		    mandatory true;
		    description
			"The source IP address.";
		    ngcliext:node-fmt "^source @@$n";
		}

		leaf tunnel-type {
		    type gre-tunnel-type;
		    description
			"One of the strings 'l3', 'teb', or 'erspan'.";
		    ngcliext:node-fmt "^$% @@%{erspan-session-id}$n";
		}
	    }
	}
    }

    container "gre-state" {
	config "false";

	description
	    "State of the GRE tunnels.";

	container gre-table {
	    description
		"GRE table.";

	    list tunnel {
		key "name";
		description
		    "GRE tunnel name.";

		leaf name {
		    type string;
		    description
			"The GRE tunnel identifier.  A unique name
			 for this GRE tunnel.";
		}

		leaf dst-ip-address {
		     type inet:ip-address-no-zone;
		     description
			"The destination IP address.";
		}

		leaf erspan-session-id {
		    type uint32 {
			range "0..1023";
		    }
		    description
			"VNI value, u24.";
		}

		leaf instance {
		    type uint32;
		    description
			"Each GRE tunnel creates an interface.  The
			 created interface will be named 'gre<X>',
			 where the <X> is the instance number.
			 The instance number must be unique across
			 all GRE entries.";

		}

		leaf encap-route-table {
		    type ngcom:rt-identifier-63;
		    description
			"Encapsulation route table name.";
		}

		leaf src-ip-address {
		     type inet:ip-address-no-zone;
		     description
			"The source IP address.";
		}

		leaf tunnel-type {
		    type gre-tunnel-type;
		    description
			"One of the strings 'l3', 'teb', or 'erspan'.";
		}
	    }
	}
    }

}
